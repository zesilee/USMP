// Code generated by crd2yang from CRD businessvlannets.biz.usmp.io; DO NOT EDIT.
// 北向 CRD 反向派生（C2Y-01）：CRD 是 schema authority，重生成用 make gen-crd2yang。
module usmp-business-vlan-net {
  namespace "urn:usmp:yang:usmp-business-vlan-net";
  prefix ubvn;

  organization "USMP";
  description
    "业务网络配置模型——由北向 CRD 反向派生（crd2yang，C2Y-01）。generated-from: businessvlannets.biz.usmp.io";

  revision 2026-08-04 {
    description "Generated from CRD businessvlannets.biz.usmp.io.";
  }

  extension task-name {
    argument name;
    description
      "任务域标记（与华为模型 task-name 语义对齐）：驱动 /yang/modules category 与前端菜单归组。";
  }

  ubvn:task-name "business-network";

  container business-vlan-net {
    description
      "业务 VLAN 打通期望配置。";
    leaf description {
      type string {
        pattern ".{1,80}";
      }
      description
        "业务描述（对齐 huawei-vlan description 长度 1..80）。";
    }
    list devices {
      key "ip";
      description
        "参与打通的设备清单。";
      leaf-list access-ports {
        type string {
          pattern ".{1,63}";
        }
        description
          "以 access 方式加入该 VLAN 的接口名（对齐 if-name 长度 1..63）。";
      }
      leaf ip {
        type string {
          pattern "([0-9]{1,3}\\.){3}[0-9]{1,3}";
        }
        description
          "设备管理 IP（列表主键，与 DeviceStore 一致）。";
      }
      leaf-list trunk-ports {
        type string {
          pattern ".{1,63}";
        }
        description
          "以 trunk 方式放行该 VLAN 的接口名（对齐 if-name 长度 1..63）。";
      }
    }
    leaf enabled {
      type boolean;
      description
        "业务使能开关。";
    }
    leaf name {
      type string {
        pattern "[A-Za-z0-9_-]{1,31}";
      }
      description
        "业务名称（对齐 huawei-vlan name 长度 1..31）。";
    }
    container qos {
      description
        "QoS 参数。";
      leaf priority {
        type uint8 {
          range "0..7";
        }
        description
          "802.1p 优先级。";
      }
    }
    leaf vlan-id {
      type uint16 {
        range "1..4094";
      }
      mandatory true;
      description
        "业务 VLAN ID（对齐 huawei-vlan vlan-id，展开到每台设备）。";
    }
    leaf vlan-type {
      type enumeration {
        enum "common";
        enum "super";
      }
      description
        "VLAN 类型（对齐 huawei-vlan vlan-type 枚举子集）。";
    }
  }
}

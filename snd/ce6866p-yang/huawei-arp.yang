/*
Copyright (C) 2020 Huawei Technologies Co., Ltd. All rights reserved.
*/
module huawei-arp {
  namespace "urn:huawei:yang:huawei-arp";
  prefix arp;
  import huawei-pub-type {
    prefix pub-type;
  }
  import huawei-network-instance {
    prefix ni;
  }
  import huawei-vlan {
    prefix vlan;
  }
  import huawei-bd {
    prefix bd;
  }
  import ietf-inet-types {
    prefix inet;
  }
  import ietf-yang-types {
    prefix yang;
  }
  import huawei-extension {
    prefix ext;
  }
  import huawei-ifm {
    prefix ifm;
  }
  import huawei-ip {
    prefix ip;
  }
  import huawei-ifm-trunk {
    prefix ifm-trunk;
  }
  import huawei-l3vpn {
    prefix l3vpn;
  }
  import huawei-ethernet {
    prefix ethernet;
  }
  organization
    "Huawei Technologies Co., Ltd.";
  contact
    "Huawei Industrial Base
     Bantian, Longgang
     Shenzhen 518129
     People's Republic of China
     Website: http://www.huawei.com
     Email: support@huawei.com";
  description
    "Address resolution protocol (ARP) management, which includes static ARP configuration, dynamic ARP learning, ARP security configuration, ARP entry query, and packet statistics collection.";
  revision 2020-04-18 {
    description
      "Add the container arp-port-security.";
    reference
      "Huawei private.";
  }
  revision 2020-03-13 {
    description
      "Modify description.";
    reference
      "Huawei private.";
  }
  revision 2020-03-04 {
    description
      "Add the leaf broadcast-max-num.";
    reference
      "Huawei private.";
  }
  revision 2020-01-13 {
    description
      "Initial revision.";
    reference
      "Huawei private.";
  }

  ext:task-name "arp";
  typedef arpstrict-learn {
    type enumeration {
      enum "force-disable" {
        value 1;
        description
          "Disable strict ARP learning on an interface.";
      }
      enum "force-enable" {
        value 2;
        description
          "Enable strict ARP learning on an interface.";
      }
      enum "trust" {
        value 3;
        description
          "Enable an interface to use global strict ARP learning policies if strict ARP learning is not enabled on the interface.";
      }
    }
    description
      "Whether to enable strict ARP learning.";
  }
  typedef arpgratuitous-send {
    type enumeration {
      enum "enable" {
        value 2;
        description
          "Enable gratuitous ARP on interface.";
      }
      enum "disable" {
        value 3;
        description
          "Disable gratuitous ARP on interface.";
      }
    }
    description
      "Whether to enable gratuitous ARP.";
  }
  typedef suppress-type {
    type enumeration {
      enum "arp" {
        value 1;
        description
          "Timestamp suppression performed on an interface board for ARP packets.";
      }
      enum "arp-miss" {
        value 2;
        description
          "Timestamp suppression performed on an interface board for ARP miss packets.";
      }
    }
    description
      "ARP suppression based on ARP message type.";
  }
  typedef suppress-ip-type {
    type enumeration {
      enum "dest-ip" {
        value 1;
        description
          "Based on destination IP timestamp suppression.";
      }
      enum "src-ip" {
        value 2;
        description
          "Based on source IP timestamp suppression.";
      }
      enum "global-port" {
        value 3;
        description
          "Global port based on timestamp suppression.";
      }
    }
    description
      "ARP suppression based on IP address type.";
  }
  typedef suppress-port-type {
    type enumeration {
      enum "src-port" {
        value 1;
        description
          "Source port based on timestamp suppression.";
      }
    }
    description
      "ARP suppression based on interface type.";
  }
  typedef arpstyle-type {
    type enumeration {
      enum "static-arp" {
        value 1;
        description
          "Static ARP entry.";
      }
      enum "dynamic-arp" {
        value 2;
        description
          "Dynamic ARP entry.";
      }
      enum "backup-arp" {
        value 3;
        description
          "Remote backup ARP entry.";
      }
      enum "interface-arp" {
        value 4;
        description
          "Interface ARP entry.";
      }
      enum "openflow-arp" {
        value 5;
        description
          "ARP entry generated based on the openflow table.";
      }
      enum "redirect-arp" {
        value 6;
        description
          "Redirect ARP.";
      }
    }
    description
      "Type of an ARP entry.";
  }
  typedef clear-type {
    type enumeration {
      enum "clear-dynamic-arp" {
        value 3;
        description
          "Clear dynamic ARP entries.";
      }
      enum "clear-backup-arp" {
        value 4;
        description
          "Clear remote backup ARP entries.";
      }
    }
    description
      "Type of an ARP clearance operation.";
  }
  typedef arpbatch-type {
    type enumeration {
      enum "batch" {
        value 1;
        description
          "Remote backup state is batch.";
      }
      enum "real" {
        value 2;
        description
          "Remote backup state is real.";
      }
    }
    description
      "ARP backup type.";
  }
  typedef import-policy {
    type enumeration {
      enum "none" {
        value 0;
        description
          "No policy.";
      }
      enum "untrust" {
        value 1;
        description
          "Untrust policy.";
      }
    }
    description
      "Type of an ARP import policy.";
  }
  typedef bridge-type {
    type enumeration {
      enum "vlan" {
        value 1;
        description
          "VLAN.";
      }
      enum "bd" {
        value 2;
        description
          "BD.";
      }
    }
    description
      "Type of an ARP bridge domain.";
  }
  typedef arpfix-type {
    type enumeration {
      enum "no-fix" {
        value 0;
        description
          "Disable the anti-attack function for fixed ARP in all modes.";
      }
      enum "fix-all" {
        value 1;
        description
          "Fixed ARP in fixed-all mode.";
      }
      enum "fix-mac" {
        value 2;
        description
          "Fixed ARP in fixed-MAC mode.";
      }
      enum "send-ack" {
        value 3;
        description
          "Fixed ARP in send ack mode.";
      }
    }
    description
      "Type of an ARP fix.";
  }
  typedef mffport-type {
    type enumeration {
      enum "no-config" {
        value 0;
        description
          "No MFF port functions.";
      }
      enum "network-port" {
        value 1;
        description
          "Network side interface.";
      }
      enum "isolate-port" {
        value 2;
        description
          "User isolate interface.";
      }
    }
    description
      "Type of an ARP MFF port type.";
  }
  typedef ipconflict-type {
    type enumeration {
      enum "local-ip-conflict" {
        value 1;
        description
          "The IP address of a local device is in conflict with that of another device.";
      }
      enum "remote-ip-conflict" {
        value 2;
        description
          "The local device serving as an access device detects that the IP addresses of its attached devices or of user terminals are in conflict.";
      }
      enum "local-ce-ip-conflict" {
        value 3;
        description
          "In a heterogeneous interworking scenario, a PE detects that its connected CE IP or MAC address is different from that configured on the PE using the local-ce ip or local-ce mac command.";
      }
    }
    description
      "Type of an ARP IP conflict.";
  }
  typedef track-opcode-type {
    type enumeration {
      enum "delete" {
        value 1;
        description
          "Deletion.";
      }
      enum "modify" {
        value 2;
        description
          "Modification.";
      }
    }
    description
      "Type of an ARP track operation code.";
  }
  typedef mffstat-flagtype {
    type enumeration {
      enum "static" {
        value 1;
        description
          "Static user type.";
      }
      enum "dynamic" {
        value 2;
        description
          "Dynamic user type.";
      }
    }
    description
      "Type of an ARP MFF statistic Flag type.";
  }
  typedef l2proxy-flag-type {
    type enumeration {
      enum "static" {
        value 1;
        description
          "Static L2 proxy ARP type.";
      }
      enum "dynamic" {
        value 2;
        description
          "Dynamic L2 proxy ARP type.";
      }
      enum "conflict" {
        value 3;
        description
          "Conflicting L2 proxy ARP type.";
      }
    }
    description
      "Type of an ARP L2 proxy flag type.";
  }
  typedef detect-mode {
    type enumeration {
      enum "loose" {
        value 0;
        description
          "In loose mode, an interface sends ARP probe messages only when both the physical status and protocol status are up.";
      }
      enum "strict" {
        value 1;
        description
          "In strict mode, an interface sends ARP probe messages when the physical status is up.";
      }
    }
    description
      "The detect mode of an interface sending ARP probe messages.";
  }
  typedef arp-packet-type {
    type enumeration {
      enum "request" {
        value 1;
        description
          "ARP request packet.";
      }
    }
    description
      "The type of ARP packet.";
  }
  typedef arp-ip-type {
    type enumeration {
      enum "dest-ip" {
        value 1;
        description
          "Destination IP address of ARP packet.";
      }
      enum "ip" {
        value 3;
        description
          "IP address of ARP packet, including source and destination IP addresses.";
      }
    }
    description
      "The address type of ARP packet.";
  }
  typedef arp-forward-type {
    type enumeration {
      enum "discard" {
        value 1;
        description
          "Discarding packets.";
      }
      enum "forward" {
        value 2;
        description
          "Forwarding packets.";
      }
    }
    description
      "The operation type of packet processing policy.";
  }
  container arp {
    description
      "Address resolution protocol (ARP) management, which includes static ARP configuration, dynamic ARP learning, ARP security configuration, ARP entry query, and packet statistics collection.";
    container global {
      description
        "Configure ARP system information.";
      leaf strict-learn-enable {
        type boolean;
        default "false";
        description
          "Enable/disable strict ARP learning so that a device learns only address information carried in the ARP reply messages in response to the ARP Request messages sent by itself.";
      }
      leaf l2topo-detect-enable {
        type boolean;
        default "false";
        description
          "Enable/disable L2 topology probe. After a L2 interface goes up, the device updates all ARP entries corresponding to the VLAN to which the L2 interface belongs.";
      }
      leaf rate-trap-interval {
        type uint32 {
          range "0..1200";
        }
        units s;
        default "0";
        description
          "Interval at which ARP logs and traps are recorded. If the value is 0, logs and traps are not recorded.";
      }
      leaf timeout-enable {
        type boolean;
        default "false";
        ext:hidden ui;
        description
          "Enable/disable ARP aging. When the life cycle of an ARP entry on an interface reaches the aging time set on the interface, the device sends ARP aging probe messages to the corresponding device. If the device cannot be probed, the ARP entry is deleted. ";
      }
      leaf passive-learn-enable {
        type boolean;
        default "false";
        description
          "Enable/disable passive ARP learning. After the backup device in a VRRP backup group receives an ARP request message destined for the virtual IP address, the backup device learns the ARP entry of the requester.";
      }
      leaf diff-learn-disable {
        type boolean;
        default "false";
        ext:hidden ui;
        description
          "Enable/disable ARP learning on different segment.";
      }
      leaf topo-detect-disable {
        type boolean;
        default "false";
        description
          "Enable/disable topology change disable.";
      }
      leaf expire-time {
        type uint32 {
          range "60..86400";
        }
        units s;
        default "1200";
        description
          "Aging time of a dynamic ARP entry. ";
      }
      leaf gratuitous-send {
        type boolean;
        default "false";
        ext:hidden ui;
        description
          "Enable/disable sending gratuitous ARP packet.";
      }
      leaf gratuitous-interval {
        when "../gratuitous-send='true'";
	    type uint32 {
          range "1..86400";
        }
	    units s;
	    ext:hidden ui;
        default "60";
        description
          "The interval of sending gratuitous arp packet.";
      }
      leaf gateway-dup-enable {
        type boolean;
        default "false";
        description
          "Enable/disable gateway duplicate.";
      }
      leaf con-send-enable {
        type boolean;
        default "false";
        description
          "Enable/disable ARP packet sending at a limited rate.";
      }
      leaf con-send-maxnum {
        when "../con-send-enable='true'";
        type uint16 {
          range "1..10";
        }
        default "5";
        description
          "Maximum packet sending rate, expressed in the number of packets send every 10 ms.";
      }
      leaf max-static-num {
        type uint32 {
          range "0..65536";
        }
        ext:hidden ui;
        default "16384";
        description
          "Set the maximum number of static ARP entries allowed to be configured on a switch.";
      }
      leaf check-type {
        type arpfix-type;
        default "no-fix";
        ext:hidden ui;
        description
          "Mode of fixed ARP.";
      }
      leaf gratuitous-drop {
        type boolean;
        default "false";
        description
          "Enable/disable the function to discard gratuitous ARP packets.";
      }
      leaf ipconflict-detect-enable {
        type boolean;
        default "false";
        description
          "Enable/disable IP address conflict check.";
      }
      leaf src-mac-check {
        type boolean;
        default "false";
        ext:hidden ui;
        description
          "Enable/disable the consistency check of source MAC addresses in ARP packets.";
      }
      leaf vlanif-expiretime {
        type uint32 {
          range "60..86400";
        }
        units s;
        default "1200";
        description
          "Aging time of a dynamic ARP entry of VLAN interface.";
      }
      container evncfg {
        description
          "Configure ARP EVN user configuration.";
        ext:hidden ui;
        leaf cache-enable {
          type boolean;
          default "false";
          description
            "Enable/disable the ARP cache proxy function for EVN users.";
        }
        leaf cache-timeout {
          type uint32 {
            range "0..1000000";
          }
          units s;
          default "240";
          description
            "Set the aging time for ARP cache entries of EVN users.";
        }
      }
      leaf gmff-enable {
        type boolean;
        ext:hidden ui;
        default "false";
        description
          "Enable/disable MFF globally.";
      }
      leaf host-conflict-period {
        type uint16 {
          range "2..36000";
        }
        units s;
        default "180";
        description
          "Period configurations for the host conflict.";
      }
      leaf host-conflict-threshold {
        type uint16 {
          range "1..1000";
        }
        default "5";
        description
          "Retry times configurations for the host conflict.";
      }
      leaf broadcast-max-num {
        type uint16 {
          range "0..3000";
        }
        default "500";
        description
          "Broadcast send max number.";
      }
      leaf multicast-learning-enable {
        type boolean;
        default "false";
        ext:hidden ui;
        description
          "Enable/disable the system to learn ARP entries with multicast MAC addresses.";
      }         
      leaf probe-times  {
        type uint8 {
          range "0..10";
        }
        ext:hidden ui;
        default "3";
        description
          "The number of aging probes for dynamic ARP entries.";
      }
      leaf snooping-enable {
        type boolean;
        default "false";
        ext:hidden ui;
        description
          "Enable/disable the ARP snooping function.";
      }
      leaf arp-fast-reply {
        type boolean;
        default "true";
        ext:hidden ui;
        description
          "Enable/disable ARP fast reply.";
      }
      leaf dfs-backup-rate {
        type uint32 {
          range "1..65535";
        }
        units s;
        default "2000";
        description
          "ARP backup rate limit.";
      }
    }
    container speed-limits {
      description
        "List of timestamp suppression rate at which an interface board suppresses ARP messages.";
      list speed-limit {
        key "slot-id suppress-type ip-type";
        description
          "Configure timestamp suppression rate at which an interface board suppresses ARP messages.";
        leaf slot-id {
          type string {
            length "1..24";
          }
          description
            "Slot ID, which refers to the position of logical MPU board and physical LPU boards. When Slot ID refering MPU board, the value of slot-id is 0.";
        }
        leaf suppress-type {
          type suppress-type;
          must "(../suppress-type='arp' and (../ip-type='dest-ip' or ../ip-type='src-ip')) or (../suppress-type='arp-miss' and ../ip-type='src-ip')";
          description
            "Suppression type. The available options are ARP and ARP miss.";
        }
        leaf ip-type {
          type suppress-ip-type;
          must "(../suppress-type='arp' and (../ip-type='dest-ip' or ../ip-type='src-ip')) or (../suppress-type='arp-miss' and ../ip-type='src-ip')";
          description
            "Suppression type based on IP addresses. The available options are destination IP suppression and source IP suppression. Destination IP suppression maps to ARP suppression. Source IP suppression maps to ARP miss suppression.";
        }
        leaf suppress-value {
          type uint32 {
            range "0..65536";
          }
          mandatory true;
          description
            "Number of ARP messages or ARP miss messages that an interface can process in a specified period.";
        }
      }
    }
    container current-speed-limits {
      config false;
      description
        "List of current timestamp suppression rate at which an interface board suppresses ARP messages.";
      list current-speed-limit {
        key "slot-id suppress-type ip-type";
        description
          "Operational state of current timestamp suppression rate at which an interface board suppresses ARP messages. When Slot ID refering MPU board, the value of slot-id is 0.";
        leaf slot-id {
          type string {
            length "1..24";
          }
          description
            "Slot ID, which refers to the position of logical MPU and LPU boards.";
        }
        leaf suppress-type {
          type suppress-type;
          description
            "Suppression type. The available options are ARP and ARP miss.";
        }
        leaf ip-type {
          type suppress-ip-type;
          description
            "Suppression type based on IP addresses. The available options are destination IP suppression and source IP suppression. Destination IP suppression maps to ARP suppression. Source IP suppression maps to ARP miss suppression.";
        }
        leaf suppress-value {
          type uint32 {
            range "0..65536";
          }
          description
            "Number of ARP messages or ARP miss messages that an interface can process in a specified period.";
        }
      }
    }
    container static-arps {
      description
        "List of short static ARP configurations, not depend on the interface.";
      list static-arp {
        must "not(/ifm:ifm/ifm:interfaces/ifm:interface[ifm:vrf-name=current()/ni-name]/ip:ipv4/arp:static-arps/arp:static-arp[arp:ip-addr=current()/ip-addr])";
        key "ip-addr ni-name";
        description
          "Configure static ARP table. By default, the system ARP table is empty, and address mappings are obtained using dynamic ARP.";
        leaf ip-addr {
          type inet:ipv4-address-no-zone;
          description
            "IP address, in dotted decimal notation.";
        }
        leaf ni-name {
          type leafref {
            path "/ni:network-instance/ni:instances/ni:instance/ni:name";
          }
          must "/ni:network-instance/ni:instances/ni:instance[ni:name=current()]/l3vpn:afs/l3vpn:af[l3vpn:type='ipv4-unicast']";
          description
            "Name of the VPN instance to which an ARP entry belongs, which refers to network instance name.";
        }
        leaf mac-addr {
          type pub-type:mac-address;
          mandatory true;
          description
            "MAC address in the format of H-H-H, in which H is a hexadecimal number of 1 to 4 bits.";
        }
        leaf vlan-id {
          type uint16 {
            range "1..4094";
          }
          description
            "VLAN ID. If this parameter is not set, the VLAN ID is considered to be 0. If this parameter is set, the ARP entry is in the specified VLAN.";
        }
        leaf vxlan-id {
          type uint32 {
            range "1..16777215";
          }
          description
            "Value of VXLAN network identifier.";
        }
        choice tunnel-ip {
          description
              "Tunnel IP address.";
          case ipv4-ip {
            description
              "Tunnel IPv4 IP address.";
            leaf source-addr {
              type inet:ipv4-address-no-zone;
              description
                "Value of tunnel source IP address.";
            }
            leaf peer-addr {
              type inet:ipv4-address-no-zone;
              description
                "Value of tunnel peer Ip address.";
            }
          }
          case ipv6-ip {
            description
              "Tunnel IPv6 IP address.";
            leaf source-ipv6-addr {
              type inet:ipv6-address-no-zone;
              description
                "Value of tunnel source IPV6 address.";
            }
            leaf peer-ipv6-addr {
              type inet:ipv6-address-no-zone;
              description
                "Value of tunnel peer IPV6 address.";
            }
          }
        }
      }
    }
    container query-entries {
      config false;
      description
        "List of ARP entries that can be queried.";
      list query-entry {
        key "ni-name ip-addr";
        config false;
        description
          "Statistics of query ARP entries, including static, dynamic, and interface-based ARP entries.";
        leaf ni-name {
          type leafref {
            path "/ni:network-instance/ni:instances/ni:instance/ni:name";
          }
          description
            "Name of the VPN instance to which an ARP entry belongs, which refers to network instance name.";
        }
        leaf ip-addr {
          type inet:ipv4-address-no-zone;
          description
            "IP address, in dotted decimal notation.";
        }
        leaf mac-addr {
          type pub-type:mac-address;
          description
            "MAC address.";
        }
        leaf expire-time {
          type uint32 {
            range "1..1440";
          }
          units s;
          description
            "Aging time of a dynamic ARP entry.";
        }
        leaf style-type {
          type arpstyle-type;
          default "static-arp";
          description
            "Type of ARP entries. An ARP entry can be a static, dynamic, remote backup, or interface based ARP entry and so on.";
        }
        leaf if-name {
          type leafref {
            path "/ifm:ifm/ifm:interfaces/ifm:interface/ifm:name";
          }
          description
            "Type and number of the interface that has learned ARP entries.";
        }
        leaf slot-id {
          type string {
            length "1..24";
          }
          description
            "Slot ID, which indicates the position of logical MPU and LPU boards. When Slot ID refering MPU board, the value of slot-id is 0.";
        }
        leaf pe-vlan {
          type uint16 {
            range "1..4094";
          }
          description
            "ID of the outer VLAN to which an ARP entry belongs.";
        }
        leaf ce-vlan {
          type uint16 {
            range "1..4094";
          }
          description
            "ID of the inner VLAN to which an ARP entry belongs.";
        }
        leaf pvc {
          type uint32;
          description
            "Interface where a PVC resides and VPI/VCI.";
        }
        leaf vni {
          type uint32 {
            range "1..16777215";
          }
          description
            "VXLAN ID.";
        }
        leaf source-addr {
          type inet:ip-address-no-zone;
          description
            "Tunnel source IP address.";
        }
        leaf peer-addr {
          type inet:ip-address-no-zone;
          description
            "Tunnel peer IP address.";
        }
        leaf work-if-name {
              type leafref {
                path "/ifm:ifm/ifm:interfaces/ifm:interface/ifm:name";
              }
              description
                "Work interface name.";
            }
      }
    }
    container global-speed-limits {
      description
        "List of timestamp suppression rate at which a device suppresses ARP messages.";
      ext:hidden ui;
      list global-speed-limit {
        key "suppress-type ip-type";
        description
          "Configure timestamp suppression rate at which a device suppresses ARP messages.";
        leaf suppress-type {
          type suppress-type;
          must "((../suppress-type='arp-miss') and (../ip-type='dest-ip')) or ((../suppress-type='arp') and (../ip-type='dest-ip')) or ((../suppress-type='arp') and (../ip-type='global-port'))";
          description
            "Suppression type. The available options are ARP and ARP miss.";
        }
        leaf ip-type {
          type suppress-ip-type;
          must "((../suppress-type='arp-miss') and (../ip-type='dest-ip')) or ((../suppress-type='arp') and (../ip-type='dest-ip')) or ((../suppress-type='arp') and (../ip-type='global-port'))";
          description
            "Suppression type based on IP addresses. The available options are destination IP suppression and source IP suppression. Destination IP suppression maps to ARP suppression. Source IP suppression maps to ARP miss suppression.";
        }
        leaf port-type {
          type suppress-port-type;
          default "src-port";
          description
            "Suppression type based on Port. ";
        }
        leaf suppress-value {
          type uint32 {
            range "0..65536";
          }
          description
            "Number of ARP messages or ARP miss messages that a device can process in a specified period.";
        }
      }
    }
    container statisticss {
      config false;
      ext:hidden ui;
      description
        "List of ARP packet statistics.";
      list statistics {
        key "slot-id";
        description
          "ARP packet statistics. ARP statistics on all boards are displayed in sequence.";
        leaf slot-id {
          type string {
            length "1..24";
          }
          description
            "Slot ID, which refers to the position of logical MPU and LPU boards.  When Slot ID refering MPU board, the value of slot-id is 0.";
        }
        leaf packets-received {
          type uint32 {
            range "0..4294967294";
          }
          description
            "Number of received ARP packets.";
        }
        leaf miss-received {
          type uint32 {
            range "0..4294967294";
          }
          description
            "Number of received ARP Miss packets.";
        }
        leaf learn-count {
          type uint32 {
            range "0..4294967294";
          }
          description
            "Number of learned ARP entries.";
        }
        leaf packets-drop-limit {
          type uint32 {
            range "0..4294967294";
          }
          description
            "Number of the ARP packets discarded due to restriction.";
        }
        leaf packets-drop-other {
          type uint32 {
            range "0..4294967294";
          }
          description
            "Number of ARP packets discarded due to other reasons.";
        }
        leaf miss-drop-limit {
          type uint32 {
            range "0..4294967294";
          }
          description
            "Number of ARP Miss packets discarded due to restriction.";
        }
        leaf miss-drop-other {
          type uint32 {
            range "0..4294967294";
          }
          description
            "Number of ARP Miss packets discarded due to other reasons.";
        }
        leaf packets-drop-speedlmt {
          type uint32 {
            range "0..4294967294";
          }
          description
            "Number of ARP packets discarded due to a rate limit.";
        }
        leaf packets-proxy-supp {
          type uint32 {
            range "0..4294967294";
          }
          description
            "Number of ARP packets discarded because of proxy suppression.";
        }
      }
    }
    container error-packets {
      config false;
      ext:hidden ui;
      description
        "List of ARP error packet information.";
      list error-packet {
        key "slot-id sequence";
        description
          "Operational state of ARP error packet on an interface.";
        leaf slot-id {
          type string {
            length "1..24";
          }
          description
            "Slot ID of the board that received the ARP error packet, which refers to the position of logical MPU and LPU boards. When Slot ID refering MPU board, the value of slot-id is 0.";
        }
        leaf sequence {
          type uint32 {
            range "1..10";
          }
          description
            "Sequence number of the received ARP error packet on each board.";
        }
        leaf if-name {
          type pub-type:if-name;
          description
            "Name of an interface.";
        }
        leaf receive-time {
          type yang:date-and-time;
          description
            "Time when an ARP error packet was received.";
        }
        leaf receive-content {
          type string {
            length "1..255";
          }
          description
            "Content of the received ARP error packet, including ARP header, the source MAC address, the source IP address, the destination MAC address, and the destination IP address.";
        }
      }
    }
    container entry-statistics {
      config false;
      ext:hidden ui;
      description
        "List of ARP entry statistics.";
      list entry-statistic {
        key "slot-id";
        description
          "ARP entry statistics. ARP entry statistics on all boards are displayed in sequence.";
        leaf slot-id {
          type string {
            length "1..24";
          }
          description
            "Slot ID, which refers to the position of logical MPU and LPU boards. When Slot ID refering MPU board, the value of slot-id is 0.";
        }
        leaf dynamic-num {
          type uint32 {
            range "0..4294967294";
          }
          description
            "Number of dynamic ARP entries.";
        }
        leaf static-num {
          type uint32 {
            range "0..4294967294";
          }
          description
            "Number of static ARP entries.";
        }
        leaf remote-num {
          type uint32 {
            range "0..4294967294";
          }
          description
            "Number of remote backup ARP entries.";
        }
        leaf redirect-num {
          type uint32 {
            range "0..4294967294";
          }
          description
            "Number of remote redirect ARP entries.";
        }
        leaf exceed-flag {
          type boolean;
          default "false";
          description
            "Flag indicating that the number of ARP entries exceeds the specification of a board.";
        }
      }
    }
    container openflow-tbls {
      config false;
      ext:hidden ui;
      description
        "List of ARP open flow tables.";
      list openflow-tbl {
        key "vni ip-addr";
        description
          "Operational state of ARP open flow tables.";
        leaf vni {
          type uint32 {
            range "1..16000000";
          }
          description
            "VXLAN ID.";
        }
        leaf ip-addr {
          type inet:ipv4-address-no-zone;
          description
            "IP address, in dotted decimal notation.";
        }
        leaf mac-addr {
          type pub-type:mac-address;
          description
            "MAC address in the format of H-H-H, in which H is a hexadecimal number of 1 to 4 bits. ";
        }
        leaf vtep-ip {
          type inet:ipv4-address-no-zone;
          description
            "Vtep IP.";
        }
      }
    }
    container duplicate-items {
      config false;
      ext:hidden ui;
      description
        "List of ARP duplicate MAC tables.";
      list duplicate-item {
        key "mac-addr bridge-type bridge-id";
        config false;
        description
          "Operational state of ARP duplicate MAC tables.";
        leaf mac-addr {
          type pub-type:mac-address;
          description
            "MAC address in the format of H-H-H, in which H is a hexadecimal number of 1 to 4 bits. ";
        }        
        leaf bridge-type {
          type bridge-type;
          description
            "Bridge type.";
        }
        leaf bridge-id {
          type uint32 {
            range "1..16777215";
          }
          description
            "Bridge ID.";
        }
        leaf if-name {
          type pub-type:if-name;
          description
            "Name of the interface that has received dup ARP.";
        }
        leaf ip-addr {
          type inet:ipv4-address-no-zone;
          description
            "IP address, in dotted decimal notation.";
        }
        leaf aging-time {
          type uint32 {
            range "1..180";
          }
          units "s";
          description
            "Expire time of duplicate MAC record.";
        }
        leaf vni {
          type uint32 {
            range "1..16777215";
          }
          description
            "VXLAN ID.";
        }
        leaf source-addr {
          type inet:ipv4-address-no-zone;
          description
            "Tunnel source IP address.";
        }
        leaf peer-addr {
          type inet:ipv4-address-no-zone;
          description
            "Tunnel dest IP address.";
        }
      }
    }
    container ip-conflicts {
      config false;
      ext:hidden ui;
      description
        "List of statistics about conflicting IP addresses detected by ARP.";
      list ip-conflict {
        key "ip-addr conflict-type sys-time conflict-count local-ifname";
        description
          "Statistics of conflicting IP addresses detected by ARP.";
        leaf ip-addr {
          type inet:ipv4-address-no-zone;
          description
            "Conflicting IP address.";
        }
        leaf conflict-type {
          type ipconflict-type;
          description
            "IP address conflict type.";
        }
        leaf sys-time {
          type yang:date-and-time;
          description
            "Date and time when an IP address conflict occurred.";
        }
        leaf conflict-count {
          type uint32 {
            range "0..4294967294";
          }
          description
            "Number of IP address conflicts.";
        }
        leaf local-ifname {
          type leafref {
            path "/ifm:ifm/ifm:interfaces/ifm:interface/ifm:name";
          }
          description
            "Interface where the conflicting IP address resides.";
        }
        leaf slot-id {
          type string {
            length "1..24";
          }
          description
            "Slot ID, which indicates the position of logical MPU and LPU boards. When Slot ID refering MPU board, the value of slot-id is 0.";
        }
        leaf suppress-count {
          type uint32 {
            range "0..4294967294";
          }
          description
            "Number of times that conflicting IP addresses are suppressed.";
        }
        leaf receive-ifname {
          type pub-type:if-name;
          description
            "Interface on which an ARP packet is received when an IP address conflict occurs.";
        }
        leaf local-vlan {
          type uint16 {
            range "0..4094";
          }
          description
            "VLAN that corresponds to the conflicting IP address.";
        }
        leaf local-cevlan {
          type uint16 {
            range "0..4094";
          }
          description
            "Outer VLAN that corresponds to the conflicting IP address.";
        }
        leaf receive-vlan {
          type uint16 {
            range "0..4094";
          }
          description
            "VLAN carried in a received ARP packet when an IP address conflict occurs.";
        }
        leaf receive-cevlan {
          type uint16 {
            range "0..4094";
          }
          description
            "Outer VLAN carried in a received ARP packet when an IP address conflict occurs.";
        }
        leaf local-mac {
          type pub-type:mac-address;
          description
            "MAC address of an interface.";
        }
        leaf receive-mac {
          type pub-type:mac-address;
          description
            "Source MAC address carried in a received ARP packet when an IP conflict occurs.";
        }
        leaf header-src-mac {
          type pub-type:mac-address;
          description
            "Source MAC address carried in the Ethernet header of a received ARP packet.";
        }
        leaf header-dst-mac {
          type pub-type:mac-address;
          description
            "Destination MAC address carried in the Ethernet header of a received ARP packet.";
        }
      }
    }
    container track-statistics {
      config false;
      ext:hidden ui;
      description
        "List of ARP track statistics.";
      list track-statistic {
        key "op-code ip-addr vlan-id old-ifname new-ifname sys-time";
        description
          "ARP track statistics.";
        leaf op-code {
          type track-opcode-type;
          description
            "Type of an operation.";
        }
        leaf ip-addr {
          type inet:ipv4-address-no-zone;
          description
            "IP address.";
        }
        leaf vlan-id {
          type leafref {
            path "/vlan:vlan/vlan:vlans/vlan:vlan/vlan:id";
          }
          description
            "VLAN ID.";
        }
        leaf old-ifname {
          type leafref {
            path "/ifm:ifm/ifm:interfaces/ifm:interface/ifm:name";
          }
          description
            "Old interface name.";
        }
        leaf new-ifname {
          type leafref {
            path "/ifm:ifm/ifm:interfaces/ifm:interface/ifm:name";
          }
          description
            "New interface name.";
        }
        leaf sys-time {
          type yang:date-and-time;
          description
            "Date and time when an IP address conflict is recorded.";
        }
        leaf mac-addr {
          type pub-type:mac-address;
          description
            "MAC address.";
        }
      }
    }
    container bd-tracks {
      config false;
      description
        "List of ARP Track Statistics on the VBDIF.";
      list bd-track {
        key "op-code ip-addr old-ifname new-ifname sys-time";
        description
          "Statistics of ARP Track on the VBDIF.";
        leaf op-code {
          type track-opcode-type;
          description
            "Type of an operation.";
        }
        leaf ip-addr {
          type inet:ipv4-address-no-zone;
          description
            "IP address.";
        }
        leaf old-ifname {
          type string {
            length "1..63";
          }
          description
            "Old interface name.";
        }
        leaf new-ifname {
          type string {
            length "1..63";
          }
          description
            "New interface name.";
        }
        leaf sys-time {
          type yang:date-and-time;
          description
            "Date and time when an IP address conflict is recorded.";
        }
        leaf bd-id {
          type leafref {
            path "/bd:bd/bd:instances/bd:instance/bd:id";
          }
          description
            "Bridge domain ID.";
        }
        leaf mac-addr {
          type pub-type:mac-address;
          description
            "MAC address.";
        }
      }
    }
    container cached-statistics {
      config false;
      ext:hidden ui;
      description
        "List of statistics about cached ARP entries of a specified EVN instance.";
      list cached-statistic {
        key "evn-name vlan-id ip-addr";
        description
          "Statistics of cached ARP entries of a specified EVN instance.";
        leaf evn-name {
          type string {
            length "1..31";
          }
          description
            "EVN instance name.";
        }
        leaf vlan-id {
          type leafref {
            path "/vlan:vlan/vlan:vlans/vlan:vlan/vlan:id";
          }
          description
            "VLAN ID.";
        }
        leaf ip-addr {
          type inet:ipv4-address-no-zone;
          description
            "IP address.";
        }
        leaf mac-addr {
          type pub-type:mac-address;
          description
            "MAC address.";
        }
        leaf if-name {
          type pub-type:if-name;
          description
            "Interface name.";
        }
        leaf aging-time {
          type uint32 {
            range "0..4294967294";
          }
          description
            "Aging time.";
        }
      }
    }
    container anti-attack-records {
      config false;
      description
        "List of ARP anti attack statistics.";
      list anti-attack-record {
        key "supp-type src-ip-addr dest-ip-addr interface attack-time";
        description
          "ARP anti-attack statistics.";
        leaf supp-type {
          type suppress-type;
          description
            "Type of suppression.";
        }
        leaf src-ip-addr {
          type inet:ipv4-address-no-zone ;
          description
            "Source IP address.";
        }
        leaf dest-ip-addr {
          type inet:ipv4-address-no-zone ;
          description
            "Destination IP address.";
        }
        leaf interface {
          type leafref {
            path "/ifm:ifm/ifm:interfaces/ifm:interface/ifm:name";
          }
          description
            "Interface name.";
        }
        leaf attack-time {
          type yang:date-and-time;
          description
            "Time when an attack occurs.";
        }
      }
    }
  }
  rpc convert-to-static {
    description
      "Convert dynamic ARP entries to static ARP entries.";
    ext:hidden ui;
    ext:node-ref "/arp/query-entries/query-entry";
    input {
      leaf if-name {
        type leafref {
          path "/arp:arp/arp:query-entries/arp:query-entry/arp:if-name";
        }
        description
          "Name of an interface where dynamic ARP entries are to be converted to static ARP entries.";
      }
    }
  }
  rpc batch-delete-vpn {
    description
      "delete static ARP entries by VPN instance.";
    ext:hidden ui;
    ext:node-ref "/arp/static-arps/static-arp";
    input {
      leaf ni-name {
        type leafref {
          path "/arp:arp/arp:static-arps/arp:static-arp/arp:ni-name";
        }
        description
          "VPN instance name of the static ARP entries to be deleted.";
      }
    }
  }
  rpc batch-delete-all {
    description
      "delete all static ARP entries";
    ext:hidden ui;
    ext:node-ref "/arp/static-arps/static-arp";
    ext:node-ref "/ifm:ifm/ifm:interfaces/ifm:interface/ip:ipv4/static-arps/static-arp";
  }

  augment "/ifm:ifm/ifm:interfaces/ifm:interface/ip:ipv4" {
    description
      "List of ARP configurations under interface.";
    container static-arps {
      description
        "List of static ARP static entry configurations.";
      list static-arp {
        key "ip-addr";
        description
          "Configure static ARP table. By default, the system ARP table is empty, and address mappings are obtained using dynamic ARP.";
        leaf ip-addr {
          type inet:ipv4-address-no-zone;
          description
            "IP address specified in this command and the IP address of the outbound interface specified by interface must be on the same network segment.";
        }
        leaf mac-addr {
          type pub-type:mac-address;
          mandatory true;
          description
            "MAC address specified in this command and can not be a broadcast address.";
        }
        leaf pevid {
          type uint16 {
            range "1..4094";
          }
          description
            "Outer VLAN ID. If this parameter is not set, the VLAN ID is considered to be 0. If this parameter is set, the ARP entry is in the specified VLAN. Please be consistent with the VLAN configuration on the interface.";
        }
        leaf cevid {
          when "../pevid";
          type uint16 {
            range "1..4094";
          }
          description
            "Inner VLAN ID. If this parameter is not set, the VLAN ID is considered to be 0. If this parameter is set, the ARP entry is in the specified VLAN. Please be consistent with the VLAN configuration on the interface.";
        }
      }
    }
  }
  augment "/ifm:ifm/ifm:interfaces/ifm:interface" {
    description
      "List of ARP configurations under ifm interface.";
    container arp-entry {
      when "not(/ifm:ifm/ifm:interfaces/ifm:interface/ifm-trunk:trunk/ifm-trunk:members/ifm-trunk:member[ifm-trunk:name=current()/../ifm:name])";
      description
        "Configure ARP interface, including the aging time, probe interval, number of aging probe attempts, dynamic ARP learning status, strict ARP learning status, and routed proxy.";
      leaf expire-time {
        type uint32 {
          range "1..86400";
        }
        units s;
        default "1200";
        description
          "Aging time of a dynamic ARP entry.";
      }
      leaf probe-interval {
        type uint32 {
          range "1..5";
        }
        units s;
        default "5";
        description
          "Interval for detecting dynamic ARP entries.";
      }
      leaf probe-times {
        type uint32 {
          range "0..10";
        }
        default "3";
        description
          "Number of aging probe attempts for a dynamic ARP entry. If a device does not receive an ARP reply message after the number of aging probe attempts reaches a specified number, the dynamic ARP entry is deleted.";
      }
      leaf arp-learn-disable {
        type boolean;
        default "false";
        description
          "Enable/disable dynamic ARP learning. If the value is true, dynamic ARP learning is disabled. If the value is false, dynamic ARP learning is enabled.";
      }
      leaf miss-anti-limit {
        when "../../ifm:type='100GE' or ../../ifm:type='25GE' or ../../ifm:type='10GE' or ../../ifm:type='40GE' or ../../ifm:type='Ethernet' or ../../ifm:type='GigabitEthernet' or ../../ifm:type='Eth-Trunk' or ../../ifm:type='Vlanif' or ../../ifm:type='MEth' or ../../ifm:type='Vbdif' or ../../ifm:type='PW-VE' or ../../ifm:type='Global-VE' or ../../ifm:type='Remote-Ap' or ../../ifm:type='Virtual-Template'";
        type uint32 {
          range "0..65536";
        }
        ext:hidden ui;
        default "0";
        description
          "The ARP MISS message rate is suppressed on the interface to limit the rate of packets or messages that exceed the rate suppression.";
      }
      leaf arp-learn-strict {
        type arpstrict-learn;
        default "trust";
        description
          "Enable strict ARP learning. After strict ARP learning is enabled, a device only learns address information of only the ARP reply message in response to the ARP request sent by itself. Strict ARP learning employs the longest match rule. 1)If strict ARP learning is configured both globally and in the interface, the strict ARP learning configuration in the interface is used. 2)If strict ARP learning is not configured in the interface, the global strict ARP learning configuration is used.";
      }
      leaf route-proxy-enable {
        type boolean;
        default "false";
        description
          "Enable/disable routed proxy ARP. When two hosts reside on different network segments and do not have default gateways configured, IP address resolution between the two hosts can be implemented using routed proxy ARP.";
      }
      leaf inner-proxy-enable {
        when "../../ifm:type!='Vbdif'";
        type boolean;
        default "false";
        description
          "Enable/disable intra-VLAN proxy ARP. Some switches isolate hosts in the same VLAN. To allow hosts in the same VLAN to communicate, enable inner VLAN proxy ARP. Only sub interface, VLANIF, vbridge and remote ap interfaces are supported.";
      }
      leaf inter-proxy-enable {
        when "../../ifm:type!='Vbdif'";
        type boolean;
        default "false";
        description
          "Enable/disable inter VLAN proxy ARP. If hosts in different VLANs need to communicate at L2, enable inter VLAN proxy ARP on an interface. Hosts between sub VLANs in a super VLAN cannot communicate by default. To allow these hosts to communicate, enable inter VLAN proxy ARP on the VLAN interface of the super VLAN. Only sub interface, VLANIF, vbridge and remote ap interfaces are supported.";
      }
      leaf local-proxy-enable {
        when "../../ifm:type='Vbdif'";
        type boolean;
        default "false";
        description
          "Enable/disable local proxy ARP. To allow isolated hosts in a bridge domain (BD) to communicate with each other, enable local proxy ARP. Only VBD interfaces are supported.";
      }
      leaf fake-expire-time {
        type uint32 {
          range "1..36000";
        }
        units s;
        default "5";
        description
          "Aging time of a fake ARP entry.";
      }
      leaf probe-unicast {
        type boolean;
        default "false";
        description
          "Enable/disable to send unicast ARP aging probe messages for a dynamic ARP entry.";
      }
      leaf dest-mac-check {
        type boolean;
        default "false";
        description
          "Enable/disable to check destination MAC addresses in ARP messages.";
      }
      leaf src-mac-check {
        type boolean;
        default "false";
        description
          "Enable/disable to check source MAC addresses in ARP messages.";
      }
      leaf distribute-enable {
        when "../../ifm:type='Vbdif'";
        type boolean;
        default "false";
        description
          "Enable/disable to distribute gateway. Only VBD interfaces are supported.";
      }
      leaf gratuitous-send {
        type arpgratuitous-send;
        default "enable";
        description
          "Enable/disable to send gratuitous ARP packet on interface.";
      }
      leaf gratuitous-interval {
        when "../gratuitous-send='enable'";
        type uint32 {
          range "1..86400";
        }
        ext:hidden ui;
        units "s";
        default "60";
        description
          "The interval of sending gratuitous ARP packet on Interface.";
      }
      leaf host-collect-enable {
        when "../../ifm:type='Vbdif'";
        type boolean;
        default "false";
        description
          "Enable/disable the host information collection function. Only VBD interfaces are supported.";
      }
      leaf import-policy {
        type import-policy;
        ext:hidden ui;
        default "none";
        description
          "The controller generates a ARP list item is not trusted, can be covered.";
      }
      leaf fast-delete {
        type boolean;
        ext:hidden ui;
        default "false";
        description
          "Enable/disable ARP delete Trigger link down.";
      }
      leaf check-type {
        type arpfix-type;
        ext:hidden ui;
        default "no-fix";
        description
          "Mode of fixed ARP on an interface.";
      }
      leaf gratuitous-drop {
        type boolean;
        ext:hidden ui;
        default "false";
        description
          "Enable/disable discarding gratuitous ARP packets on an interface.";
      }
      leaf l2proxy-isolate-enable {
        type boolean;
        ext:hidden ui;
        default "false";
        description
          "Enable/disable configuration of a user-isolate interface.";
      }
      leaf mffport-type {
        type mffport-type;
        ext:hidden ui;
        default "no-config";
        description
          "MFF interface functions.";
      }
      leaf real-expire-time {
        type uint32 {
          range "60..86400";
        }
        config false;
        description
          "real aging time of a dynamic ARP entry.";
      }
      leaf anyway-proxy-enable {
        type boolean;
        default "false";
        description
          "Enable/disable anyway proxy ARP. When two hosts reside on different network segments and do not have default gateways configured, IP address resolution between the two hosts can be implemented using anyway proxy ARP.";
      }
      leaf link-down-delete {
        when "../../ifm:type='Vlanif'";
        type boolean;
        default "false";
        description
          "Enable/disable the function to delete ARP entries immediately after a link goes down.";
      }
      leaf generate-rdtbl-enable {
        when "../../ifm:type='Vbdif'";
        type boolean;
        default "false";
        description
          "Enable/disable the configuration of generate rd table. It's mutually exclusive with the configuration of enable L2 proxy under the corresponding BD instance.";
      }
      leaf broadcast-detect-interval {
        when "../../ifm:type='Vbdif'";
        type uint32 {
          range "1..5";
        }
        units s;
        default "5";
        description
          "Configure the broadcast detect interval. Only VBD interfaces are supported.";
      }
      leaf broadcast-detect-times {
        when "../../ifm:type='Vbdif'";
        type uint32 {
          range "1..10";
        }
        default "3";
        description
          "Configure the broadcast detect times. Only VBD interfaces are supported.";
      }
      leaf broadcast-detect-enable {
        when "../../ifm:type='Vbdif'";
        type boolean;
        default "false";
        description
          "Enable/disable the configuration of broadcast detect. Only VBD interfaces are supported.";
      }
      leaf fake-penalty-time {
        type uint32 {
          range "1..180";
        }
        units s;
        default "5";
        description
          "Aging penalty time of a fake ARP entry.";
      }
      leaf gratuitous-arp-drop {
        when "../../ifm:type!='Vbdif'";
        type boolean;
        default "false";
        description
          "Enable/disable an interface to discard gratuitous ARP packets.";
      }
      leaf multicast-learning-enable {
        type boolean;
        ext:hidden ui;
        default "false";
        description
          "Enable/disable the interface to learn ARP entries with multicast MAC addresses.";
      }
      leaf snooping-enable {
        type boolean;
        ext:hidden ui;
        default "false";
        description
          "Enable/disable ARP snooping function.";
      }
      leaf arp-miss-disable {
        when "../../ifm:type='Vbdif'";
        type boolean;
        ext:hidden ui;
        default "false";
        description
          "Enable/disable ARP miss function in vbdif.";
      }
      leaf broadcast-max-num {
        when "(../../ethernet:ethernet/ethernet:l3-sub-interface/ethernet:dot1q-termination) or (../../ethernet:ethernet/ethernet:l3-sub-interface/ethernet:qinq-termination)";
        type uint16 {
          range "0..500";
        }
        units "pps";
        default "0";
        description
          "Maximum broadcast packet sending rate, expressed in the number of packets sent per second.";
      }
      leaf smart-discover-enable {
        when "../../ifm:type='Vlanif'";
        type boolean;
        default "false";
        description
          "Enable/disable ARP smart discover. Only VLANIF interfaces are supported.";
      }
    }
    container arp-limits {
      description
        "List of maximum number of dynamic ARP entries that an interface can learn.";
      list arp-limit {
        key "vlan-id";
        description
          "Configure maximum number of dynamic ARP entries that an interface can learn. If the number of ARP entries that an interface can learn changes and the number of the learned ARP entries exceeds the changed value, the interface cannot learn additional ARP entries. The system prompts you to delete the excess ARP entries.";
        leaf vlan-id {
          type uint16 {
            range "0..4094";
          }
          description
            "ID of the VLAN where ARP learning is restricted. This parameter can be set only on Layer 2 interfaces and sub-interfaces. Ethernet, GE, VE, and Eth-Trunk interfaces can be both Layer 3 and Layer 2 interfaces. When they work in Layer 3 mode, they cannot have VLANs configured. When they work in Layer 2 mode, they must have VLANs configured. Ethernet, GE, and Eth-Trunk sub-interfaces can be both common and QinQ sub-interfaces. ";
        }
        leaf limit-num {
          type uint32 {
            range "1..65536";
          }
          mandatory true;
          description
            "Maximum number of dynamic ARP entries that an interface can learn.";
        }
        leaf learned-num {
          type uint32 {
            range "0..65536";
          }
          ext:hidden ui;
          config false;
          description
            "Number of ARP entries that an interface has already learned.";
        }
        leaf threshold-value {
          type uint32 {
            range "60..100";
          }
          ext:hidden ui;
          default "80";
          description
            "Alarm threshold for maximum number of ARP entries that an interface can learn.";
        }
      }
    }
    container arp-status-detect {
      description
        "Configure ARP entry status detect.";
      leaf ip-addr {
        type inet:ipv4-address-no-zone;
        description
          "Detect IP.";
      }
      leaf mode {
        when "../ip-addr";
        type detect-mode;
        default "strict";
        description
          "Detect mode.";
      }
      leaf times {
        when "../ip-addr";
        type uint8 {
          range "1..10";
        }
        default "3";
        description
          "Detect times.";
      }
      leaf interval {
        when "../ip-addr";        
        type uint32 {
          range "200..10000";
        }
        units "ms";
        default "1000";
        description
          "Detect interval.";
      }
    }
    container arp-port-security {
      description
        "Configure ARP port security.";
           container l2-sub-interface {
              when "../../ifm:l2-mode-enable='true'";
              description
                "Configure ARP security policy on Layer 2 sub-interface.";
              leaf l2proxy-dyn-learn {
                type boolean;
                default "true";
                description
                  "Enable/disable dynamic ARP learning of L2 proxy ARP.";
              }
              leaf l2proxy-max-num {
                type uint32 {
                  range "0..1048576";
                }
                default "0";
                description
                  "Maximum number of ARP entries allowed for L2 proxy ARP.";
              }
        }
    }
    container packet-policys {
    when "../ifm:type='Vbdif'";
    description
      "List of packet processing policies based on the IP addresses of ARP packets.";
    list packet-policy {
      key "packet-type ip-type ip-addr";
      description
        "Configure a packet processing policy based on the IP addresses of ARP packets.";
      leaf packet-type {
        type arp-packet-type;
        description
          "ARP packet type. Currently, only request packet is supported.";
      }
      leaf ip-type {
        type arp-ip-type;
        description
          "IP address type. Currently, only destination IP is supported.";
      }
      leaf ip-addr {
        type inet:ipv4-address-no-zone;
        description
          "Specifies the IP address.";
      }
      leaf operation {
        type arp-forward-type;
        mandatory true;
        description
          "Packet processing policy, such as discard and forward.";
      }
    }
    }
    container arp-statistics {
      config false;
      description
        "Operational state of ARP statistics on interfaces.";
      leaf recv-req-packets {
        type uint32 {
          range "0..4294967294";
        }
        description
          "Number of ARP request messages received.";
      }
      leaf recv-reply-packets {
        type uint32 {
          range "0..4294967294";
        }
        description
          "Number of ARP reply messages received.";
      }
      leaf recv-gratis-packets {
        type uint32 {
          range "0..4294967294";
        }
        description
          "Number of gratuitous ARP messages received.";
      }
      leaf send-req-packets {
        type uint32 {
          range "0..4294967294";
        }
        description
          "Number of ARP request messages send.";
      }
      leaf send-reply-packets {
        type uint32 {
          range "0..4294967294";
        }
        description
          "Number of ARP reply messages send.";
      }
      leaf send-gratis-packets {
        type uint32 {
          range "0..4294967294";
        }
        description
          "Number of gratuitous ARP messages send.";
      }
      leaf exceed-flag {
        type boolean;
        ext:hidden ui;
        description
          "Flag indicating that the number of ARP entries exceeds the specification of an interface.";
      }
      leaf batch-state {
        type arpbatch-type;
        ext:hidden ui;
        description
          "The ARP batch state of Interface.";
      }
    }
  }
  augment "/vlan:vlan/vlan:vlans/vlan:vlan" {
    description
      "List of ARP configurations under VLAN interface.";
    container arp-ip-pool {
      description
        "Configure IP address pools based on sub-VLANs.";
      leaf ip-begin {
        type inet:ipv4-address-no-zone ;
        description
          "Start IP address.";
      }
      leaf ip-end {
        type inet:ipv4-address-no-zone;
        must "../ip-begin";
        description
          "End IP address.";
      }
    }
    container arp-security {
      ext:hidden ui;
      description
        "Configure ARP VLAN security configuration.";
      leaf dynamic-enable {
        type boolean;
        default "false";
        description
          "Enable/disable dynamic ARP probe function.";
      }
      leaf l2proxy-enable {
        type boolean;
        must "../dhcpsnoop-enable='false'";
        default "false";
        description
          "Enable/disable Layer 2 ARP proxy.";
      }
      leaf l2proxy-expire-time {
        when "../l2proxy-enable='true'";
        type uint32 {
          range "1..62640";
        }
        default "900";
        description
          "Aging time for Layer 2 proxy ARP entries.";
      }
      leaf l2proxy-dyn-learn {
        when "../l2proxy-enable='true'";
        type boolean;
        default "true";
        description
          "Enable/disable dynamic ARP learning of L2 proxy ARP.";
      }
      leaf l2proxy-max-num {
        when "../l2proxy-enable='true'";
        type uint32 {
          range "1..32768";
        }
        default "2000";
        description
          "Maximum number of ARP entries allowed for L2 proxy ARP.";
      }
      leaf dhcpsnoop-enable {
        type boolean;
        must "../l2proxy-enable='false'";
        default "false";
        description
          "Enable/disable the egress ARP inspection function.";
      }
      leaf snooping-enable {
        type boolean;
        default "false";
        description 
          "Enable/disable the ARP snooping function.";
      }
      container check-items {
        description
          "Configure check items of ARP binding table matching check in a VLAN.";
        leaf interface {
          type boolean;
          default "true";
          description
            "Enable/disable checking of interface information during ARP binding table matching check.";
        }
        leaf ip-check {
          type boolean;
          default "true";
          description
            "Enable/disable checking of the IP address during ARP binding table matching check.";
        }
        leaf mac-check {
          type boolean;
          default "true";
          description
            "Enable/disable checking of the MAC address during ARP binding table matching check.";
        }
      }
    }
    container arp-rate-limit {
      ext:hidden ui;
      description
        "Configure rate limit for ARP packets in a VLAN configuration.";
      leaf suppress-type {
        type suppress-type;
        description
          "Type of ARP suppression for attack defense in a VLAN.";
      }
      leaf suppress-value {
        type uint32 {
          range "0..65536";
        }
        default "0";
        description
          "ARP suppression threshold for attack defense in a VLAN.";
      }
    }
    container arp-mff {
      ext:hidden ui;
      description
        "Configure MFF configurations, including VLAN ID, gateway probe, dynamic ARP learning, maximum number of dynamic users, servers, static gateway address, and online user detection.";
      leaf mff-enable {
        type boolean;
        must "/arp:arp/arp:global/arp:gmff-enable='true'";
        default "false";
        description
          "Enable/disable the MFF function.";
      }
      leaf gateway-detect-enable {
        when "../mff-enable='true'";
        type boolean;
        default "false";
        description
          "Enable/disable the timed gateway detection function.";
      }
      leaf dynlearn-enable {
        when "../mff-enable='true'";
        type boolean;
        default "true";
        description
          "Enable/disable dynamic ARP learning.";
      }
      leaf max-user-num {
        when "../mff-enable='true'";        
        type uint32 {
          range "10..2000";
        }
        description
          "Configuration of the maximum number of users allowed in a VLAN.";
      }
      leaf static-gateway-ipaddr {
        when "../mff-enable='true'";
        type inet:ipv4-address-no-zone;
        description
          "Configuration of the IP address of a static gateway in a VLAN.";
      }
      leaf trans-req-enable {
        when "../mff-enable='true'";
        type boolean;
        default "false";
        description
          "Enable/disable the function of transparently transmiting ARP request packets.";
      }
      container server-ips {
        when "../mff-enable='true'";
        description
          "List of server configuration list.";
        list server-ip {
          key "ip-addr";
          description
            "Configure server configuration.";
          leaf ip-addr {
            type inet:ipv4-address-no-zone;
            description
              "Configuration of a server IP address in a network.";
          }
        }

      }
    }
    container arp-l2proxys {
      ext:hidden ui;
      config false;
      description
        "List of Layer 2 proxy ARP statistics.";
      list arp-l2proxy {
        key "ip-addr";
        description
          "L2 proxy ARP statistics.";
        leaf ip-addr {
          type inet:ipv4-address-no-zone ;
          description
            "IP address.";
        }
        leaf if-name {
          type leafref {
            path "/ifm:ifm/ifm:interfaces/ifm:interface/ifm:name";
          }
          description
            "Interface name.";
        }
        leaf mac-addr {
          type pub-type:mac-address;
          description
            "MAC address.";
        }
        leaf aging-time {
          type uint32 {
            range "1..62640";
          }
          description
            "Aging time.";
        }
        leaf status {
          type l2proxy-flag-type;
          description
            "L2 proxy ARP status.";
        }
      }
    }
    container arp-statisticss {
      ext:hidden ui;
      config false;
      description
        "List of MFF statistics.";
      list arp-statistics {
        key "gateway-ip";
        description
          "Operational state of MFF information, including VLAN ID, gateway IP address, gateway MAC address, user IP address, user MAC address, interface, and user type.";
        leaf gateway-ip {
          type inet:ipv4-address-no-zone;
          description
            "Gateway IP address.";
        }
        leaf gateway-mac {
          type pub-type:mac-address;
          description
            "Gateway MAC address.";
        }
        container user-entries {
          description
            "List of MFF user information.";
          list user-entry {
            key "ip-addr";
            description
              "Operational state of MFF user information, including user IP address, user MAC address, interface, and user type.";
            leaf ip-addr {
              type inet:ipv4-address-no-zone;
              description
                "IP address of an access user.";
            }
            leaf mac-addr {
              type pub-type:mac-address;
              description
                "MAC address of an MFF access user.";
            }
            leaf if-name {
              type leafref {
                path "/ifm:ifm/ifm:interfaces/ifm:interface/ifm:name";
              }
              description
                "Name of an interface on which MFF is enabled.";
            }
            leaf user-type {
              type mffstat-flagtype;
              description
                "MFF user type.";
            }
          }
        }
      }
    }
  }


  augment "/bd:bd/bd:instances/bd:instance" {
    description
      "List of ARP configurations under bridge-domain interface.";
    container arp-list {
      description
        "Configure ARP bridge domain.";
      leaf l2proxy-enable {
        type boolean;
        default "false";
        description
            "Enable/disable L2 proxy. It's mutually exclusive with the configuration of generating redirect ARP under the corresponding VBD interface.";
      }
      choice broadcast-suppress {
        description
          "ARP broadcast suppress function.";			
        case enable {
          description
            "ARP broadcast suppress.";
          leaf broadcast-suppress-enable {
            type empty;
            description
              "Enable/disable ARP broadcast suppress.";
          }
        }
        case mismatch-discard-enable {
          description
            "ARP broadcast suppress mismatch discard.";			  
          leaf broadcast-suppress-discard {
            type empty;
            description
              "Enable/disable ARP broadcast suppress mismatch discard.";
          }
        }			  
      }
      leaf l2proxy-gw-enable {
        when "../broadcast-suppress-enable or ../broadcast-suppress-discard";
        type boolean;
        default "false";
        description
          "Enable/disable L2 proxy gateway mac.";
      }
      leaf l2proxy-expire-time {
        when "../l2proxy-enable='true'";
        type uint32 {
          range "1..62640";
        }
        units s;
        default "900";
        description
          "Set L2 proxy expire-Time.";
      }
      leaf collect-host-enable {
        when "../l2proxy-enable='true'";
        type boolean;
        default "false";
        description
          "Enable/disable L2 proxy collect-host.";
      }
      leaf rate-limit {
        type uint32 {
          range "0..65536";
        }
        default "0";
        ext:hidden ui;
        description
          "ARP suppression threshold for attack defense in a BD.";
      }
      leaf dynamic-enable {
        type boolean;
        ext:hidden ui;
        default "false";
        description
          "Enable/disable the dynamic ARP probe function.";
      }
      container check-item {
        ext:hidden ui;
        description
          "Configure Checking items of ARP binding table matching check in a BD.";
        leaf vxlan-tunnel {
          type boolean;
          default "true";
          description
            "Enable/disable checking of VXLAN information during ARP binding table matching check.";
        }
        leaf ip-check {
          type boolean;
          default "true";
          description
            "Enable/disable checking of the IP address during ARP binding table matching check.";
        }
        leaf mac-check {
          type boolean;
          default "true";
          description
            "Enable/disable checking of the MAC address during ARP binding table matching check.";
        }
      }
    }
    container arp-user-entry {
      config false;
      ext:hidden ui;
      description
        "Operational state of ARP broadcast suppress user information.";
      leaf ip-addr {
        type inet:ipv4-address-no-zone;
        description
          "IP address, in dotted decimal notation.";
      }
      leaf mac-addr {
        type pub-type:mac-address;
        description
          "MAC address in the format of H-H-H, in which H is a hexadecimal number of 1 to 4 bits. ";
      }
      leaf vtep {
        type inet:ipv4-address-no-zone;
        description
          "VXLAN tunnel source IP.";
      }
      leaf flag {
        type string {
          length "1..24";
        }
        description
          "ARP broadcast suppress type.";
      }
    }
    container arp-statistics {
      config false;
      description
        "ARP bridge domain packet statistics.";
      leaf receive-req-packets {
        type uint32;
        description
          "Number of ARP request packets received in a BD of a L2 service.";
      }
      leaf receive-gratis-packets {
        type uint32;
        description
          "Number of gratuitous ARP packets received in a BD of a L service.";
      }
      leaf receive-proxy-packets {
        type uint32;
        description
          "Number of proxy ARP packets received in a BD of a L2 service.";
      }
      leaf receive-reply {
        type uint32;
        description
          "Number of ARP reply packets received in a BD of a L2 service.";
      }
      leaf miss-discard {
        type uint32;
        description
          "Number of packets discarded due to ARP broadcast suppression.";
      }
      leaf discard-other {
        type uint32;
        description
          "Number of packets discarded due to reasons other than ARP broadcast suppression.";
      }
      leaf receive-total-packets {
        type uint32;
        description
          "Total number of received ARP packets in a BD of a L2 service.";
      }
      leaf send-unicast-packets {
        type uint32;
        description
          "Number of send unicast ARP packets in a BD of a L2 service.";
      }
      leaf send-broadcast-packets {
        type uint32;
        description
          "Number of send broadcast ARP packets in a BD of a L2 service, excluding gratuitous ARP and proxy ARP packets.";
      }
      leaf send-gratis-packets {
        type uint32;
        description
          "Number of send gratuitous ARP packets in a BD of a L2 service.";
      }
      leaf send-proxy-packets {
        type uint32;
        description
          "Number of send proxy ARP packets in a BD of a L2 service.";
      }
      leaf l2proxy-reply {
        type uint32;
        description
          "Number of send proxy ARP packets in a BD of a L2 service.";
      }
      leaf send-total-packets {
        type uint32;
        description
          "Total number of send ARP packets in a BD of a L2 service.";
      }
    }
  }

}

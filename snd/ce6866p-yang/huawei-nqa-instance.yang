/*
Copyright (C) 2019-2020 Huawei Technologies Co., Ltd. All rights reserved.
*/
submodule huawei-nqa-instance {
  yang-version 1;
  belongs-to huawei-nqa {
    prefix nqa;
  }

  import huawei-pub-type {
    prefix pub-type;
  }
  import ietf-inet-types {
    prefix inet;
  }
  import huawei-network-instance {
    prefix ni;
  }
  import huawei-ifm {
    prefix ifm;
  }
  import ietf-yang-types {
    prefix "yang";
  }
  import huawei-extension {
    prefix ext;
  }
  include huawei-nqa-testflow;

  organization
    "Huawei Technologies Co., Ltd.";
  contact
    "Huawei Industrial Base
     Bantian, Longgang
     Shenzhen 518129
     People's Republic of China
     Website: http://www.huawei.com
     Email: support@huawei.com";
  description
    "Description of submodule NQA-instance.";

  revision 2020-03-09 {
    description
      "Modify send-trap-bits.";
    reference
      "Huawei private.";
  }
  revision 2020-02-19 {
    description
      "Modify ni-name.";
    reference
      "Huawei private.";
  }
  revision 2020-02-14 {
    description
      "Modify execution-policy.";
    reference
      "Huawei private.";
  }
  revision 2020-02-13 {
    description
      "Modify TCP and ICMP Jitter.";
    reference
      "Huawei private.";
  }
  revision 2020-02-06 {
    description
      "Modify execution-policy.";
    reference
      "Huawei private.";
  }
  revision 2020-01-15 {
    description
      "Delete next-hop of icmp-input.";
    reference
      "Huawei private.";
  }
  revision 2020-01-11 {
    description
      "Modify execution-policy to rpc.";
    reference
      "Huawei private.";
  }
  revision 2019-12-12 {
    description
      "ICMP modification.";
    reference
      "Huawei private.";
  }
  revision 2019-10-30 {
    description
      "Init revision.";
    reference
      "Huawei private.";
  }
  typedef path-type {
    type enumeration {
      enum "bypass" {
        value 1;
        description
          "Bypath.";
      }
    }
    description
      "Path type.";
  }

  typedef ethsvc-profile {
    type enumeration {
      enum profile-none {
        value 0;
        description
          "None profile.";
      }
      enum profile-imix {
        value 1;
        description
          "Imix profile.";
      }
    }
    description
      "Description of ethsvc-profile.";
  }

  typedef jitter-code-type {
    type enumeration {
      enum none {
        value 1;
        description
          "None.";
      }
      enum g711a {
        value 2;
        description
          "G711a.";
      }
      enum g711u {
        value 3;
        description
          "G711u.";
      }
      enum g729a {
        value 4;
        description
          "G729a.";
      }
    }
    description
      "Description of jitter-code-type.";
  }

  typedef jitter-mode-type {
    type enumeration {
      enum icmp-echo {
        value 2;
        description
          "Icmp echo.";
      }
      enum icmp-timestamp {
        value 1;
        description
          "Icmp timestamp.";
      }
    }
    description
      "Description of jitter-mode-type.";
  }

  typedef time-unit-type {
    type enumeration {
      enum microsecond {
        value 1;
        description
          "Microsecond timestamp.";
      }
      enum millisecond {
        value 0;
        description
          "Millisecond timestamp.";
      }
    }
    description
      "Description of time-unit-type.";
  }

  typedef recv-time-unit-type {
    type enumeration {
      enum unknown {
        value 0;
        description
          "Unknown timestamp.";
      }
      enum microsecond {
        value 2;
        description
          "Microsecond timestamp.";
      }
      enum millisecond {
        value 1;
        description
          "Millisecond timestamp.";
      }
    }
    description
      "Description of recv-time-unit-type.";
  }

  typedef vxlan-reply-mode {
    type enumeration {
      enum no-reply {
        value 1;
        description
          "No reply.";
      }
      enum udp {
        value 2;
        description
          "UDP.";
      }
      enum vxlan {
        value 3;
        description
          "VXLAN.";
      }
    }
    description
      "Description of vxlan-reply-mode.";
  }

  typedef lsp-reply-mode-type {
    type enumeration {
      enum no-reply {
        value 1;
        description
          "NQA test packets are not to be responded.";
      }
      enum udp {
        value 2;
        description
          "UDP packets are used to respond NQA test packets.";
      }
      enum level-control-channel {
        value 4;
        description
          "Control-channel packets are used to respond to NQA test packets.";
      }
    }
    description
      "Description of lsp-reply-mode-type.";
  }

  typedef srte-lsp-reply-mode-type {
    type enumeration {
      enum udp {
        value 2;
        description
          "UDP packets are used to respond NQA test packets.";
      }
    }
    description
      "Description of srte-lsp-reply-mode-type.";
  }

  typedef ip-lsp-reply-mode-type {
    type enumeration {
      enum no-reply {
        value 1;
        description
          "NQA test packets are not to be responded.";
      }
      enum udp {
        value 2;
        description
          "UDP packets are used to respond NQA test packets.";
      }
    }
    description
      "Description of ip-lsp-reply-mode-type.";
  }

  typedef lsp-path {
    type enumeration {
      enum working {
        value 0;
        description
          "Use working tunnel.";
      }
      enum hot-standby {
        value 1;
        description
          "Use hot standby tunnel.";
      }
      enum primary {
        value 2;
        description
          "Use primary tunnel.";
      }
    }
    description
      "Description of lsp-path.";
  }

  typedef remote-fec-type {
    type enumeration {
      enum null {
        value 0;
        description
          "Null.";
      }
      enum ldp {
        value 1;
        description
          "Ldp.";
      }
    }
    description
      "Description of remote-fec-type.";
  }

  typedef ttl-mode {
    type enumeration {
      enum uniform {
        value 1;
        description
          "Uniform.";
      }
      enum pipe {
        value 2;
        description
          "Pipe.";
      }
    }
    description
      "Description of ttl-mode.";
  }

  typedef vc-type {
    type enumeration {
      enum ldp {
        value 1;
        description
          "Ldp.";
      }
    }
    description
      "Description of vc-type.";
  }

  typedef lsp-version {
    type enumeration {
      enum rfc4379 {
        value 2;
        description
          "Rfc4379.";
      }
      enum ptn-mode {
        value 3;
        description
          "Ptn-mode.";
      }
    }
    description
      "Description of lsp-version.";
  }

  typedef vpls-reply-mode-type {
    type enumeration {
      enum no-reply {
        value 1;
        description
          "No-reply.";
      }
      enum udp {
        value 2;
        description
          "UDP.";
      }
      enum udp-via-vpls {
        value 5;
        description
          "UDP-via-vpls.";
      }
    }
    description
      "Description of vpls-reply-mode-type.";
  }

  typedef pw-type {
    type enumeration {
      enum atm-aal5 {
        value 2;
        description
          "ATM aal5.";
      }
      enum atm-cell-transport {
        value 3;
        description
          "ATM cell transport.";
      }
      enum vlan {
        value 4;
        description
          "VLAN.";
      }
      enum ethernet {
        value 5;
        description
          "Ethernet.";
      }
      enum hdlc {
        value 6;
        description
          "High - level Data Link Control.";
      }
      enum ppp {
        value 7;
        description
          "Point - to - Point Protocol.";
      }
      enum atm-nto1-vcc {
        value 9;
        description
          "ATM n to one VCC cell mode.";
      }
      enum atm-nto1-vpc {
        value 10;
        description
          "ATM n to one VPC cell mode.";
      }
      enum ip-layer2 {
        value 11;
        description
          "IP layer 2.";
      }
      enum atm-1to1-vcc {
        value 12;
        description
          "ATM one to one VCC cell mode.";
      }
      enum atm-1to1-vpc {
        value 13;
        description
          "ATM one to one VPC cell mode.";
      }
      enum satop-e1 {
        value 17;
        description
          "Satop e1.";
      }
      enum cesopsn-basic {
        value 21;
        description
          "Cesopsn basi.";
      }
      enum ip-interworking {
        value 64;
        description
          "IP interworking.";
      }
    }
    description
      "Description of pw-type.";
  }

  typedef lsp-jitter-type {
    type enumeration {
      enum ipv4 {
        value 0;
        description
          "The test-type of LSP jitter is IPv4.";
      }
      enum te {
        value 1;
        description
          "The test-type of LSP jitter is te.";
      }
    }
    description
      "Description of lsp-jitter-type.";
  }

  typedef test-measure-type {
    type enumeration {
      enum delay {
        value 1;
        description
          "Delay Test.";
      }
      enum loss {
        value 2;
        description
          "Loss Test.";
      }
      enum throughput {
        value 3;
        description
          "Throughput Test.";
      }
    }
    description
      "Description of test-measure-type.";
  }

  typedef test-rate-type {
    type enumeration {
      enum information-rate {
        value 2;
        description
          "Information rate.";
      }
      enum utilized-line-rate {
        value 1;
        description
          "Utilized line rate.";
      }
    }
    description
      "Description of test-rate-type.";
  }

  typedef test-ratio-unit-type {
    type enumeration {
      enum 10e-4 {
        value 0;
        description
          "10e-4.";
      }
      enum 10e-9 {
        value 1;
        description
          "10e-9.";
      }
    }
    description
      "Description of test-ratio-unit-type.";
  }

  typedef pwe3-label-type {
    type enumeration {
      enum label-alert {
        value 1;
        description
          "Label alert.";
      }
      enum control-word {
        value 2;
        description
          "Control word.";
      }
      enum normal {
        value 3;
        description
          "Normal.";
      }
    }
    description
      "Description of pwe3-label-type.";
  }

  typedef start-now-type {
    type enumeration {
      enum start-now {
        value 1;
        description
          "Start now.";
      }
    }
    description
      "Start now.";
  }
  typedef stop-type {
    type enumeration {
      enum stop {
        value 1;
        description
          "Stop.";
      }
    }
    description
      "Stop.";
  }
  grouping instances-type {
    description
      "The network quality assurance.";
    list instance {
      key "admin-name test-name";
      description
        "Test instance.";
      leaf admin-name {
        type string {
          length "1..32";
        }
        description
          "Administrator name.";
      }
      leaf test-name {
        type string {
          length "1..32";
        }
        description
          "Test name.";
      }
      choice type {
        description
          "The test-type of instance.";
        case icmp {
          description
            "ICMP NQA test.";
          container icmp-input {
            must "not(ipv4-next-hop and (ni-name != '_public_' or fwd-if-name or path-type = 'bypass'))";
            must "not(ipv6-next-hop and (ni-name != '_public_' or fwd-if-name or path-type = 'bypass'))";
            must "not(path-type = 'bypass' and (pass-route = 'true' or fwd-if-name or ipv6-dest-address or ipv6-source-address or ipv6-next-hop))";
            must "not(pass-route = 'true' and fwd-if-name)";
            must "not(out-if-name and fwd-if-name)";
            presence "ICMP PING test instance.";
            description
              "Icmp test intance input.";
            uses icmp-intance-input;
          }
        }
        case trace {
          description
            "TRACE NQA test.";
          container trace-input {
            presence "Present enable trace test intance input.";
            description
              "Trace test intance input.";
            uses trace-intance-input;
          }
        }
        case udp {
          ext:hidden ui;
          description
            "UDP NQA test.";
          container udp-input {
            presence "Present enable UDP test intance input.";
            description
              "Udp test intance input.";
            uses udp-intance-input;
          }
        }
        case tcp {
          description
            "TCP NQA test.";
          container tcp-input {
            presence "Present enable TCP test intance input.";
            description
              "Tcp test intance input.";
            uses tcp-intance-input;
          }
        }
        case dns {
          description
            "DNS NQA test.";
          container dns-input {
            presence "Present enable DNS test intance input.";
            description
              "Dns test intance input.";
            uses dns-intance-input;
          }
        }
        case jitter {
          description
            "Jitter NQA test that tests UDP-packet jitter.";
          container jitter-input {
            presence "Present enable UDP jitter test intance input";
            description
              "Jitter test intance input.";
            uses jitter-intance-input;
          }
        }
        case icmp-jitter {
          description
            "ICMP jitter NQA test.";
          container icmp-jitter-input {
            presence "Present enable ICMP jitter test intance input.";
            description
              "Icmp jitter test intance input.";
            uses icmp-jitter-intance-input;
          }
        }
        case path-jitter {
          ext:hidden ui;
          description
            "Path jitter NQA test.";
          container path-jitter-input {
            presence "Present enable path jitter test intance input.";
            description
              "Path jitter test intance input.";
            uses path-jitter-intance-input;
          }
        }
        case path-mtu {
          ext:hidden ui;
          description
            "Path MTU NQA test.";
          container path-mtu-input {
            presence "Present enable path mtu test intance input.";
            description
              "Path mtu test intance input.";
            uses path-mtu-intance-input;
          }
        }
        case vxlan-ping {
          ext:hidden ui;
          description
            "VXLAN ping NQA test.";
          container vxlan-ping-input {
            presence "Present enable VXLAN ping test intance input.";
            description
              "Vxlanping test intance input.";
            uses vxlanping-intance-input;
          }
        }
        case lsp-ping {
          ext:hidden ui;
          description
            "LSP ping NQA test.";
          container lsp-ping-input {
            presence "Present enable LSP ping test intance input.";
            description
              "Lspping test intance input.";
            uses lspping-intance-input;
          }
        }
        case lsp-trace {
          ext:hidden ui;
          description
            "LSP trace NQA test.";
          container lsp-trace-input {
            presence "Present enable LSP trace test intance input.";
            description
              "Lsptrace test intance input.";
            uses lsptrace-intance-input;
          }
        }
        case lsp-jitter {
          ext:hidden ui;
          description
            "LSP jitter NQA test.";
          container lsp-jitter-input {
            presence "Present enable LSP jitter test intance input";
            description
              "Lsptjitter test intance input.";
            uses lsp-jitter-intance-input;
          }
        }
        case pwe3-ping {
          ext:hidden ui;
          description
            "PWE3 ping NQA test.";
          container pwe3-ping-input {
            presence "Present enable PWE3 ping test intance input.";
            description
              "Pwe3ping test intance input.";
            uses pwe3-ping-intance-input;
          }
        }
        case pwe3-trace {
          ext:hidden ui;
          description
            "PWE3 trace NQA test.";
          container pwe3-trace-input {
            presence "Present enable PWE3 trace test intance input";
            description
              "Pwe3trace test intance input.";
            uses pwe3-trace-intance-input;
          }
        }
        case vpls-pw-ping {
          ext:hidden ui;
          description
            "VPLS pw ping NQA test.";
          container vpls-pw-ping-input {
            presence "Present enable VPLS PW ping test intance input.";
            description
              "Vplspwping test intance input.";
            uses vpls-pw-ping-intance-input;
          }
        }
        case vpls-pw-trace {
          ext:hidden ui;
          description
            "VPLS pw trace NQA test.";
          container vpls-pw-trace-input {
            presence "Present enable VPLS PW trace test intance input.";
            description
              "Vplspwtrace test intance input.";
            uses vpls-pw-trace-intance-input;
          }
        }
        case vpls-mac-ping {
          ext:hidden ui;
          description
            "VPLS MAC ping NQA test.";
          container vpls-mac-ping-input {
            presence "Present enable VPLS MAC ping test intance input.";
            description
              "Vplsmacping test intance input.";
            uses vpls-mac-ping-intance-input;
          }
        }
        case general-flow {
          ext:hidden ui;
          description
            "Generalflow NQA test.";
          container general-flow-input {
            presence "Present enable generalflow test intance input.";
            description
              "General flow test intance input.";
            uses general-flow-intance-input;
          }
        }
        case ethernet-service {
          ext:hidden ui;
          description
            " Ethernet service NQA test.";
          container ethernet-service-input {
            presence "Present enable ethernet service test intance input.";
            description
              "Ethernet service test intance input.";
            uses ethernet-service-intance-input;
          }
        }
      }
      container execution-policy {
        config false;
        description
          "The test intance execution policy.";
        choice execution-policy {
          description
            "The test intance start policy.";
          case start {
            description
              "Start the test.";
            choice start-type {
              description
                "The test intance start type.";
              case start-now {
                description
                  "Start now.";
                leaf start-now {
                  type start-now-type;
                  description
                    "Start the test intance instantly.";
                }
                choice start-now-end-type {
                  description
                    "Test intance end type.";
                  case at {
                    description
                      "Stop the test at the specified time.";
                    leaf start-now-end-date-time {
                      type yang:date-and-time;
                      description
                        "The test intance end time.";
                    }
                  }
                  case delay {
                    description
                      "Stop the test after the specified delay time.";
                    leaf start-now-end-delay-seconds {
                      type uint32 {
                        range "6..86399";
                      }
                      description
                        "The test intance end delay seconds.";
                    }
                  }
                  case lifetime {
                    description
                      "Stop the test after the specified life time.";
                    leaf start-now-end-lifetime-seconds {
                      type uint32 {
                        range "6..86399";
                      }
                      description
                        "The test intance end lifetime seconds.";
                    }
                  }
                }
              }
              case start-at {
                description
                  "Execute at the specified time.";
                leaf start-date-time {
                  type yang:date-and-time;
                  description
                    "The test intance start time.";
                }
                choice start-at-end-type {
                  description
                    "Test intance end type.";
                  case at {
                    description
                      "Stop the test at the specified time.";
                    leaf start-at-end-date-time {
                      type yang:date-and-time;
                      description
                        "The test intance end time.";
                    }
                  }
                  case delay {
                    description
                      "Stop the test after the specified delay time.";
                    leaf start-at-end-delay-seconds {
                      type uint32 {
                        range "6..86399";
                      }
                      description
                        "The test intance end delay seconds.";
                    }
                  }
                  case lifetime {
                    description
                      "Stop the test after the specified life time.";
                    leaf start-at-end-lifetime-seconds {
                      type uint32 {
                        range "6..86399";
                      }
                      description
                        "The test intance end lifetime seconds.";
                    }
                  }
                }
              }
              case start-delay {
                description
                  "Delay some time then execute testcase.";
                leaf start-delay-seconds {
                  type uint32 {
                    range "1..86399";
                  }
                  description
                    "The test intance start delay seconds.";
                }
                choice start-delay-end-type {
                  description
                    "Test intance end type.";
                  case at {
                    description
                      "Stop the test at the specified time.";
                    leaf start-delay-end-date-time {
                      type yang:date-and-time;
                      description
                        "The test intance end time.";
                    }
                  }
                  case delay {
                    description
                      "Stop the test after the specified delay time.";
                    leaf start-delay-end-delay-seconds {
                      type uint32 {
                        range "6..86399";
                      }
                      description
                        "The test intance end delay seconds.";
                    }
                  }
                  case lifetime {
                    description
                      "Stop the test after the specified life time.";
                    leaf start-delay-end-lifetime-seconds {
                      type uint32 {
                        range "6..86399";
                      }
                      description
                        "The test intance end lifetime seconds.";
                    }
                  }
                }
              }
              case start-daily {
                description
                  "Execute the test intance daily.";
                leaf daily-start-time {
                  type pub-type:time;
                  description
                    "Start time of daily execution.";
                }
                leaf daily-start-date {
                  type pub-type:date;
                  description
                    "Start date of daily execution.";
                }
                leaf daily-end-time {
                  type pub-type:time;
                  description
                    "End time of daily execution.";
                }
                leaf daily-end-date {
                  type pub-type:date;
                  description
                    "End date of daily execution.";
                }
              }
            }
          }
          case stop{
            description
              "Stop the test.";
            leaf stop {
              type stop-type;
              description
                "Stop the test.";
            }
          }
        }
      }
    }
  }
  
  grouping send-trap-enable {
    description
      "Enable the send trap function.";
    leaf send-trap-bits {
      type bits {
        bit owd-ds {
          position 0;
          description
            "Indicates that a trap is sent when the OWD from the destination to
             the source exceeds the threshold.

             This parameter applies only to jitter test instances.";
        }
        bit owd-sd {
          position 1;
          description
            "Indicates that a trap is sent when the OWD from the source to the
             destination exceeds the threshold.

             This parameter applies only to jitter test instances.";
        }
        bit probefailure {
          position 2;
          description
            "Indicates that a trap is sent when the OWD from the source to the
             destination exceeds the threshold.

             This parameter applies only to jitter test instances.";
        }
        bit rtd {
          position 3;
          description
            "Indicates that a trap is sent when the RTD exceeds the threshold.";
        }
        bit testcomplete {
          position 4;
          description
            "Indicates that a trap is sent when a test succeeds.";
        }
        bit testfailure {
          position 5;
          description
            "Indicates that a trap is sent when the number of test failures reaches the threshold.";
        }
        bit jitter-sd {
          position 6;
          description
            "Indicates that a trap is sent when the jitter from the source to the
             destination exceeds the threshold.

             This parameter applies to jitter/ICMPjitter test instances.";
        }
        bit jitter-ds {
          position 7;
          description
            "Indicates that a trap is sent when the jitter from the destination to
             the source exceeds the threshold.

             This parameter applies to jitter/ICMPjitter test instances.";
        }
        bit testresult-change {
          position 8;
          description
            "Indicates that a trap is sent when the probe result changes.

             This function supports only ICMP test instances.";
        }
      }
      description
        "Configures conditions for sending traps.";
    }
  }

  grouping icmp-intance-input {
    description
      "Icmp test intance input parameters.";
    choice address {
      description
        "Address information.";
      case ipv4-address {
        description
          "IPv4 address.";
        leaf ipv4-dest-address {
          type inet:ipv4-address-no-zone;
          description
            "Destination IPv4 address.";
        }
        leaf ipv4-source-address {
          type inet:ipv4-address-no-zone;
          description
            "Source IPv4 address.";
        }
        leaf ipv4-next-hop {
          type inet:ipv4-address-no-zone;
          description
            "IPv4 next hop address.";
        }
      }
      case ipv6-address {
        description
          "IPv6 address.";
        leaf ipv6-dest-address {
          type inet:ipv6-address-no-zone;
          description
            "Destination IPv6 address.";
        }
        leaf ipv6-source-address {
          type inet:ipv6-address-no-zone;
          description
            "Source IPv6 address.";
        }
        leaf ipv6-next-hop {
          type inet:ipv6-address-no-zone;
          description
            "IPv6 next hop address.";
        }
      }
    }
    leaf ni-name {
      type leafref {
        path "/ni:network-instance/ni:instances/ni:instance/ni:name";
      }
      default "_public_";
      description
        "Name of a VPN instance.";
    }
    leaf out-if-name {
      type leafref {
        path "/ifm:ifm/ifm:interfaces/ifm:interface/ifm:name";
      }
      description
        "Out interface name.";
    }
    leaf fwd-if-name {
      type leafref {
        path "/ifm:ifm/ifm:interfaces/ifm:interface/ifm:name";
      }
      description
        "Simulated inbound-interface name.";
    }
    leaf interval {
      type uint32 {
        range "1..60";
      }
      units "s";
      default "4";
      description
        "Interval for sending packets.";
    }
    leaf probe-count {
      type uint32 {
        range "1..15";
      }
      default "3";
      description
        "Number of sent packets.";
    }
    leaf timeout {
      type uint32 {
        range "1..60";
      }
      units "s";
      default "3";
      description
        "Time to wait for a response packet after a test packet is sent.";
    }
    leaf frequency {
      type uint32 {
        range "1..604800";
      }
      units "s";
      description
        "Test instance frequency. The Frequency must be greater than the value of the following formula; otherwise, the test results may be inaccurate:
         (Number of Sent Packets - 1) * (Packet Sending Interval) + (Timeout Period)";
    }
    leaf fail-percent {
      type uint32 {
        range "1..100";
      }
      units "%";
      default "100";
      description
        "Loss ratio (%), determining whether the test is sucessful.";
    }
    leaf data-size {
      type uint32 {
        range "0..8100";
      }
      units "Byte";
      default "0";
      description
        "Packet size (byte).";
    }
    leaf data-fill {
      type string {
        length "1..230";
      }
      description
        "Packing string.";
    }
    leaf tos {
      type uint16 {
        range "0..255";
      }
      ext:hidden ui;
      default "0";
      description
        "ToS.";
    }
    leaf ttl {
      type uint8 {
        range "1..255";
      }
      default "30";
      description
        "Time to live.";
    }
    leaf pass-route {
      type boolean;
      default "false";
      description
        "If not check pass route.";
    }
    leaf probe-fails {
      type uint32 {
        range "1..15";
      }
      default "1";
      description
        "Packet failed threshold determining whether send traps or events.";
    }
    leaf test-fails {
      type uint32 {
        range "1..15";
      }
      default "1";
      description
        "Test failed threshold determining whether send traps or events.";
    }
    leaf send-trap-bits {
      type bits {
        bit probefailure {
          position 31;
          description
            "Indicates that a trap is sent when the OWD from the source to the
             destination exceeds the threshold.

             This parameter applies only to jitter test instances.";
        }
        bit rtd {
          position 28;
          description
            "Indicates that a trap is sent when the RTD exceeds the threshold.";
        }
        bit testcomplete {
          position 29;
          description
            "Indicates that a trap is sent when a test succeeds.";
        }
        bit testfailure {
          position 30;
          description
            "Indicates that a trap is sent when the number of test failures reaches the threshold.";
        }
      }
      description
        "Configures conditions for sending traps.";
    }
    leaf compatibility {
      type boolean;
      default "false";
      description
        "Compatibility mode. When the ptn79 interworks with the ptn39, the no result is converted to failed and success.";
    }
    leaf next-hop-dhcp {
      type boolean;
      ext:hidden ui;
      default "false";
      description
        "Next hop DHCP.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf path-type {
      type path-type;
      description
        "Path type.";
    }
    leaf threshold-rtd {
      type uint32 {
        range "1..60000";
      }
      description
        "RTD threshold.";
    }
  }

  grouping udp-intance-input {
    description
      "Udp test intance input parameters.";
    leaf dest-address {
      type inet:ip-address-no-zone;
      description
        "Destination IP address.";
    }
    leaf source-address {
      type inet:ip-address-no-zone;
      description
        "Source IP address.";
    }
    leaf dest-port {
      type uint16 {
        range "1..65535";
      }
      default "7";
      description
        "UDP destination port.";
    }
    leaf source-port {
      type uint16 {
        range "1..65535";
      }
      description
        "UDP source port.";
    }
    leaf ttl {
      type uint8 {
        range "1..255";
      }
      default "30";
      description
        "Time to live.";
    }
    leaf data-size {
      type uint16 {
        range "0..8100";
      }
      default "0";
      description
        "Packet size (byte).";
    }
    leaf data-fill {
      type string {
        length "1..230";
      }
      description
        "Packing string.";
    }
    leaf pass-route {
      type boolean;
      default "false";
      description
        "If not check pass route.";
    }
    leaf probe-count {
      type uint32 {
        range "1..15";
      }
      default "3";
      description
        "Number of probes.";
    }
    uses send-trap-enable;
    leaf threshold-rtd {
      type uint32 {
        range "1..60000";
      }
      description
        "RTD threshold.";
    }
    leaf probe-failtimes {
      type uint32 {
        range "1..15";
      }
      default "1";
      description
        "Packet failed threshold determining whether send traps or events.";
    }
    leaf test-failtimes {
      type uint32 {
        range "1..15";
      }
      default "1";
      description
        "Test failed threshold determining whether send traps or events.";
    }
    leaf tos {
      type uint16 {
        range "0..255";
      }
      default "0";
      description
        "TOS.";
    }
    leaf fail-percent {
      type uint32 {
        range "1..100";
      }
      default "100";
      description
        "Loss ratio (%), determining whether the test is sucessful.";
    }
    leaf interval {
      type uint32 {
        range "1..60";
      }
      units "s";
      default "4";
      description
        "Interval for sending packets.";
    }
    leaf ni-name {
      type leafref {
        path "/ni:network-instance/ni:instances/ni:instance/ni:name";
      }
      description
        "Name of a VPN instance.";
    }
    leaf timeout {
      type uint32 {
        range "1..60";
      }
      units "s";
      default "3";
      description
        "Time to wait for a response packet after a test packet is sent.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      units "s";
      description
        "Test instance frequency. The Frequency must be greater than the value of the following formula; otherwise, the test results may be inaccurate:
         (Number of sent packets - 1) * (Packet sending interval) + (Timeout period).";
    }
  }

  grouping jitter-intance-input {
    description
      "Jitter test intance input parameters.";
    choice address {
      description
        "IP address configurations.";
      case ipv4-address {
        description 
          "IPv4 address.";
        leaf ipv4-dest-address  {
          type inet:ipv4-address-no-zone;
          description
            "Destination IPv4 address.";
        }     
        leaf ipv4-source-address {
          type inet:ipv4-address-no-zone;
          description
          "Source IPv4 address.";
        }
      }
      case ipv6-address {
        description 
          "IPv6 address.";
        leaf ipv6-dest-address {
          type inet:ipv6-address-no-zone;
          description
            "Destination IPv6 address.";
        }     
        leaf ipv6-source-address {
          type inet:ipv6-address-no-zone;
          description
          "Source IPv6 address.";
        }
      }
    }
    leaf dest-port {
      type uint16 {
        range "1..65535";
      }
      description
        "UDP destination port.";
    }
    leaf source-port {
      type uint16 {
        range "1..65535";
      }
      description
        "UDP source port.";
    }
    leaf ttl {
      type uint8 {
        range "1..255";
      }
      default "30";
      description
        "Time to live.";
    }
    leaf hardware-enable {
      type boolean;
      must "not(../data-fill)";
      default "false";
      description
        "Packets are sent by hardware.";
    }
    leaf interval {
      type uint32 {
        range "10..60000";
      }
      units "ms";
      must "../hardware-enable = 'false' and ../interval >= 20 or ../hardware-enable = 'true'";
      default "20";
      description
        "Interval for sending packets.";
    }
    leaf probe-count {
      type uint32 {
        range "1..15";
      }
      default "3";
      description
        "Number of probes.";
    }
    leaf jitter-packet-num {
      type uint32 {
        range "1..3000";
      }
      default "20";
      description
        "Number of sent packets.";
    }
    leaf data-size {
      type uint16 {
        range "0..8100";
      }
      units "Byte";
      default "0";
      description
        "Packet size.";
    }
    leaf data-fill {
      type string {
        length "1..230";
      }
      must "../hardware-enable = 'false'";
      description
        "Packing string.";
    }
    leaf pass-route {
      type boolean;
      default "false";
      description
        "Sending packet pass route.";
    }
    leaf tos {
      type uint16 {
        range "0..255";
      }
      default "0";
      description
        "TOS.";
    }
    leaf ni-name {
      type leafref {
        path "/ni:network-instance/ni:instances/ni:instance/ni:name";
      }
      default "_public_";
      description
        "Name of a VPN instance.";
    }
    leaf code-type {
      type jitter-code-type;
      default "none";
      description
        "Code type.";
    }
    leaf adv-factor {
      when "../code-type='g711a' or ../code-type='g711u' or ../code-type='g729a'";
      type uint8 {
        range "0..20";
      }
      default "0";
      description
        "Advantage factor.";
    }
    leaf threshold-owd-ds {
      type uint32 {
        range "1..60000";
      }
      description
        "One way delay threshold value from destination to source.";
    }
    leaf threshold-owd-sd {
      type uint32 {
        range "1..60000";
      }
      description
        "One way delay threshold value from source to destination.";
    }
    leaf threshold-rtd {
      type uint32 {
        range "1..60000";
      }
      description
        "Round trip delay time threshold value.";
    }
    leaf send-trap-bits {
      type bits {
        bit owd-ds {
          position 26;
            description
            "Indicates that a trap is sent when the OWD from the destination to
             the source exceeds the threshold.
             This parameter applies only to jitter test instances.";
        }
        bit owd-sd {
          position 27;
          description
            "Indicates that a trap is sent when the OWD from the source to the
             destination exceeds the threshold.
             This parameter applies only to jitter test instances.";
        }
        bit rtd {
          position 28;
          description
            "Indicates that a trap is sent when the RTD exceeds the threshold.";
          }
        bit testfailure {
          position 30;
          description
            "Indicates that a trap is sent when the number of test failures reaches the threshold.";
          }
      }
      description
        "Configures conditions for sending traps.";
    }
    leaf fail-percent {
      type uint32 {
        range "1..100";
      }
      units "%";
      default "100";
      description
        "Loss ratio, determining whether the test is sucessful.";
    }
    leaf test-failtimes {
      type uint32 {
        range "1..15";
      }
      default "1";
      description
        "Test failed threshold determining whether send traps or events.";
    }
    leaf timestamp {
      type time-unit-type;
      must "../hardware-enable = 'true' or ../timestamp != 'microsecond'";
      default "millisecond";
      description
        "The unit of timestamp.";
    }
    leaf out-if-name {
      type leafref {
        path "/ifm:ifm/ifm:interfaces/ifm:interface/ifm:name";
      }
      description
        "Out interface name.";
    }
    leaf timeout {
      type uint32 {
        range "1..60";
      }
      units "s";
      default "3";
      description
        "Time to wait for a response packet after a test packet is sent.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      units "s";
      description
        "Test instance frequency. The Frequency must be greater than the value of the following formula; otherwise, the test results may be inaccurate:
         (Number of Sent Packets - 1) * (Packet Sending Interval) + (Timeout Period)";
    }
  }

  grouping icmp-jitter-intance-input {
    description
      "Icmp jitter test intance input parameters.";
    choice address {
      description
        "IP address configurations.";
      case ipv4-address {
        description 
          "IPv4 address.";
        leaf ipv4-dest-address  {
          type inet:ipv4-address-no-zone;
          description
            "Destination IPv4 address.";
        }     
        leaf ipv4-source-address {
          type inet:ipv4-address-no-zone;
          description
          "Source IPv4 address.";
        }
      }
      case ipv6-address {
        description 
          "IPv6 address.";
        leaf ipv6-dest-address {
          type inet:ipv6-address-no-zone;
          description
            "Destination IPv6 address.";
        }     
        leaf ipv6-source-address {
          type inet:ipv6-address-no-zone;
          description
          "Source IPv6 address.";
        }
      }
    }
    leaf ttl {
      type uint8 {
        range "1..255";
      }
      default "30";
      description
        "Time to live.";
    }
    leaf probe-count {
      type uint32 {
        range "1..15";
      }
      default "3";
      description
        "Number of probes.";
    }
    leaf hardware-enable {
      type boolean;
      must "not(../jitter-mode='icmp-echo') or (../jitter-mode='icmp-echo' and (../hardware-enable='false'))";
      default "false";
      description
        "Packets are sent by hardware.";
    }
    leaf jitter-packet-num {
      type uint32 {
        range "1..3000";
      }
      default "20";
      description
        "Number of packets.";
    }
    leaf data-size {
      type uint16 {
        range "0..8100";
      }
      units "Byte";
      default "0";
      description
        "Packet size.";
    }
    leaf data-fill {
      type string {
        length "1..230";
      }
      must "../jitter-mode='icmp-echo' or (not(../jitter-mode='icmp-echo') and not(../data-fill))";
      description
        "Packing string.";
    }
    leaf tos {
      type uint16 {
        range "0..255";
      }
      default "0";
      description
        "TOS.";
    }
    leaf ni-name {
      type leafref {
        path "/ni:network-instance/ni:instances/ni:instance/ni:name";
      }
      default "_public_";
      description
        "Name of a VPN instance.";
    }
    leaf jitter-mode {
      type jitter-mode-type;
      default "icmp-timestamp";
      description
        "Packet format.";
    }
    leaf interval {
      type uint32 {
        range "10..60000";
      }
      units "ms";
      default "20";
      description
        "Interval for sending packets.";
    }
    leaf timestamp {
      type time-unit-type;
      must "(../hardware-enable='true' and (../timestamp='microsecond' or ../timestamp='millisecond') ) or ((not(../hardware-enable='true') and (../timestamp='millisecond') ))";
      default "millisecond";
      description
        "The unit of timestamp.";
    }
    leaf out-if-name {
      type leafref {
        path "/ifm:ifm/ifm:interfaces/ifm:interface/ifm:name";
      }
      description
        "Out interface name.";
    }
    leaf timeout {
      type uint32 {
        range "1..60";
      }
      units "s";
      default "3";
      description
        "Time to wait for a response packet after a test packet is sent.";
    }
    leaf receive-timeunit {
      type recv-time-unit-type;
      must "(../hardware-enable='true' and (../receive-timeunit='unknown' or ../receive-timeunit='microsecond' or ../receive-timeunit='millisecond') ) or ((not(../hardware-enable='true') and (../receive-timeunit='unknown') ))";
      default "unknown";
      description
        "The unit of receive timestamp.";
    }
    leaf fail-percent {
      type uint32 {
        range "1..100";
      }
      units "%";
      default "100";
      description
        "Loss ratio, determining whether the test is sucessful.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      units "s";
      description
        "Test instance frequency. The Frequency must be greater than the value of the following formula; otherwise, the test results may be inaccurate:
         (Number of Sent Packets - 1) * (Packet Sending Interval) + (Timeout Period).";
    }
  }

  grouping trace-intance-input {
    description
      "Trace test intance input parameters.";
    leaf dest-address {
      type inet:ip-address-no-zone;
      description
        "Destination IP address.";
    }
    leaf source-address {
      type inet:ip-address-no-zone;
      description
        "Source IP address.";
    }
    leaf dest-port {
      type uint16 {
        range "1..65535";
      }
      default "33434";
      description
        "TRACE destination port number.";
    }
    leaf timeout {
      type uint32 {
        range "1..60";
      }
      units "s";
      default "3";
      description
        "Time to wait for a response packet after a test packet is sent.";
    }
    leaf first-ttl {
      type uint8 {
        range "1..255";
      }
      must '(../max-ttl and ../first-ttl<=../max-ttl) or ((not(../max-ttl) and ../first-ttl<=../max-ttl))';
      default "1";
      description
        "Packet first TTL.";
    }
    leaf max-ttl {
      type uint8 {
        range "1..255";
      }
      must '(../first-ttl and ../max-ttl>=../first-ttl) or ((not(../first-ttl) and ../max-ttl>=../first-ttl))';
      default "30";
      description
        "Packet maximum TTL.";
    }
    leaf probe-count {
      type uint32 {
        range "1..15";
      }
      must '(../probe-count and ../probe-count<=10) or ((not(../probe-count) and ../probe-count<=10))';
      default "3";
      description
        "Number of sent packets.";
    }
    leaf data-size {
      type uint32 {
        range "0..8100";
      }
      default "0";
      description
        "Packet size (byte).";
    }
    leaf data-fill {
      type string {
        length "1..230";
      }
      description
        "Data padding.";
    }
    leaf pass-route {
      type boolean;
      default "false";
      description
        "If not check pass route.";
    }
    leaf ni-name {
      type leafref {
        path "/ni:network-instance/ni:instances/ni:instance/ni:name";
      }
      description
        "Name of a VPN instance.";
    }
    leaf tos {
      type uint16 {
        range "0..255";
      }
      default "0";
      description
        "TOS Field.";
    }
    leaf out-if-name {
      type leafref {
        path "/ifm:ifm/ifm:interfaces/ifm:interface/ifm:name";
      }
      description
        "Out interface name.";
    }
    leaf next-hop {
      ext:hidden ui;
      type inet:ipv4-address-no-zone;
      description
        "Next hop address.";
    }
    leaf hop-fail-times {
      type uint32 {
        range "1..255";
      }
      default "5";
      description
        "The times of hop failure.";
    }
    leaf non-fragment {
      type boolean;
      default "false";
      description
        "The mark of message no fragment.";
    }
    leaf test-fail-times {
      type uint32 {
        range "1..15";
      }
      default "1";
      description
        "Test failed threshold determining whether send traps or events.";
    }
    leaf threshold-rtd {
      type uint32 {
        range "1..60000";
      }
      description
        "RTD threshold.";
    }
    uses send-trap-enable;
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      must '(../frequency and ../frequency>=60) or ((not(../frequency) and ../frequency>=60))';
      description
        "Test instance frequency (s).";
    }
  }

  grouping tcp-intance-input {
    description
      "TCP test intance input parameters.";
    leaf dest-address {
      type inet:ipv4-address-no-zone;
      description
        "Destination IP address.";
    }
    leaf source-address {
      type inet:ipv4-address-no-zone;
      description
        "Source IP address.";
    }
    leaf interval {
      type uint32 {
        range "1..60";
      }
      units "s";
      default "4";
      description
        "Interval for sending packets.";
    }
    leaf timeout {
      type uint32 {
        range "1..60";
      }
      units "s";
      default "3";
      description
        "Time to wait for a response packet after a test packet is sent.";
    }
    leaf ttl {
      type uint8 {
        range "1..255";
      }
      default "30";
      description
        "TTL value of NQA test packets.";
    }
    leaf probe-count {
      type uint32 {
        range "1..15";
      }
      default "3";
      description
        "Number of sent packets.";
    }
    leaf tos {
      type uint16 {
        range "0..255";
      }
      default "0";
      description
        "TOS Field.";
    }
    leaf dest-port {
      type uint16 {
        range "1..65535";
      }
      default "7";
      description
        "TCP destination port number.";
    }
    leaf source-port {
      type uint16 {
        range "1..65535";
      }
      description
        "TCP source port number.";
    }
    leaf pass-route {
      type boolean;
      must "../pass-route='true'";
      default "false";
      description
        "If not check pass route.";
    }
    leaf ni-name {
      type leafref {
        path "/ni:network-instance/ni:instances/ni:instance/ni:name";
      }
      default "_public_";
      description
        "Name of a VPN instance.";
    }
    leaf threshold-rtd {
      type uint32 {
        range "1..60000";
      }
      description
        "RTD threshold.";
    }
    leaf probe-fails {
      type uint32 {
        range "1..15";
      }
      default "1";
      description
        "Packet failed threshold determining whether send traps or events.";
    }
    leaf fail-percent {
      type uint32 {
        range "1..100";
      }
      units "%";
      default "100";
      description
        "The rate of loss that the test case performed successfully.";
    }
    leaf test-fail-times {
      type uint32 {
        range "1..15";
      }
      default "1";
      description
        "Test failed threshold determining whether send traps or events.";
    }
    uses send-trap-enable;
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      units "s";
      description
        "Test instance frequency. The Frequency must be greater than the value of the following formula; otherwise, the test results may be inaccurate:
         (Number of Sent Packets - 1) * (Packet Sending Interval) + (Timeout Period).";
    }
  }

  grouping path-jitter-intance-input {
    description
      "Path jitter test intance input parameters.";
    leaf dest-address {
      type inet:ipv4-address-no-zone {
        length "1..255";
      }
      description
        "Destination IP address.";
    }
    leaf source-address {
      type inet:ipv4-address-no-zone;
      description
        "Source IP address.";
    }
    leaf fail-percent {
      type uint32 {
        range "1..100";
      }
      default "100";
      description
        "Loss ratio (%), determining whether the test is sucessful.";
    }
    leaf timeout {
      type uint32 {
        range "1..60";
      }
      units "s";
      default "3";
      description
        "Time to wait for a response packet after a test packet is sent.";
    }
    leaf first-ttl {
      type uint8 {
        range "1";
      }
      default "1";
      description
        "Packet first TTL.";
    }
    leaf max-ttl {
      type uint8 {
        range "1..255";
      }
      default "30";
      description
        "Packet maximum TTL.";
    }
    leaf interval {
      type uint32 {
        range "10..60000";
      }
      units "ms";
      default "20";
      description
        "Interval for sending packets.";
    }
    leaf probe-count {
      type uint32 {
        range "1..15";
      }
      default "3";
      description
        "Number of probes.";
    }
    leaf jitter-packet-num {
      type uint32 {
        range "1..3000";
      }
      default "20";
      description
        "Number of packets.";
    }
    leaf data-size {
      type uint16 {
        range "0..8100";
      }
      must "../jitter-mode='icmp-echo' or (not(../jitter-mode='icmp-echo') and not(../data-size))";
      default "0";
      description
        "Packet size (byte).";
    }
    leaf data-fill {
      type string {
        length "1..230";
      }
      must "../jitter-mode='icmp-echo' or (not(../jitter-mode='icmp-echo') and not(../data-fill))";
      description
        "Packing string.";
    }
    leaf jitter-mode {
      type jitter-mode-type;
      default "icmp-timestamp";
      description
        "Packet format.";
    }
    leaf tos {
      type uint16 {
        range "0..255";
      }
      default "0";
      description
        "TOS.";
    }
    leaf ni-name {
      type leafref {
        path "/ni:network-instance/ni:instances/ni:instance/ni:name";
      }
      description
        "Name of a VPN instance.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping path-mtu-intance-input {
    description
      "Path mtu test intance input parameters.";
    leaf dest-address {
      type inet:ipv4-address-no-zone;
      description
        "Destination IP address.";
    }
    leaf source-address {
      type inet:ipv4-address-no-zone;
      description
        "Source IP address.";
    }
    leaf ni-name {
      type leafref {
        path "/ni:network-instance/ni:instances/ni:instance/ni:name";
      }
      description
        "Name of a VPN instance.";
    }
    leaf max-mtu {
      type uint16 {
        range "48..9198";
      }
      default "1500";
      description
        "Max mtu.";
    }
    leaf step {
      type uint16 {
        range "1..512";
      }
      default "10";
      description
        "Test step.";
    }
    leaf probe-count {
      type uint32 {
        range "1..15";
      }
      default "3";
      description
        "Number of probes.";
    }
    leaf timeout {
      type uint32 {
        range "1..60";
      }
      units "s";
      default "3";
      description
        "Time to wait for a response packet after a test packet is sent.";
    }
    leaf out-if-name {
      type leafref {
        path "/ifm:ifm/ifm:interfaces/ifm:interface/ifm:name";
      }
      description
        "Out interface name.";
    }
    leaf result-num {
      type uint32 {
        range "1..10";
      }
      default "5";
      description
        "Result record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping dns-intance-input {
    description
      "Dns test intance input parameters.";
    leaf url-address {
      type string {
        length "1..230";
      }
      description
        "URL address.";
    }
    leaf source-address {
      type inet:ipv4-address-no-zone;
      description
        "Source IP address.";
    }
    leaf dns-server-address {
      type inet:ipv4-address-no-zone;
      description
        "Dns Server Address.";
    }
    leaf timeout {
      type uint32 {
        range "1..60";
      }
      units "s";
      default "3";
      description
        "Time to wait for a response packet after a test packet is sent.";
    }
    leaf probe-failtimes {
      type uint32 {
        range "1..15";
      }
      default "1";
      description
        "Packet failed threshold determining whether send traps or events.";
    }
    leaf test-failtimes {
      type uint32 {
        range "1..15";
      }
      default "1";
      description
        "Test failed threshold determining whether send traps or events.";
    }
    leaf ni-name {
      type leafref {
        path "/ni:network-instance/ni:instances/ni:instance/ni:name";
      }
      description
        "Name of a VPN instance.";
    }
    leaf threshold-rtd {
      type uint32 {
        range "1..60000";
      }
      description
        "Round trip delay time threshold value.";
    }
    uses send-trap-enable;
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping vxlanping-intance-input {
    description
      "Vxlan ping test intance input parameters.";
    leaf vxlan-source-address {
      type inet:ip-address-no-zone;
      description
        "The source address of the NVE interface.";
    }
    leaf vxlan-peer-address {
      type inet:ip-address-no-zone;
      description
        "The address of the remote NVE.";
    }
    leaf vni {
      type uint32 {
        range "1..16777215";
      }
      description
        "The ID of the VNI.";
    }
    leaf dest-udp-port {
      type uint16 {
        range "1..65535";
      }
      description
        "Destination Port Number.";
    }
    leaf source-address {
      type inet:ip-address-no-zone;
      description
        "The source address of the inner packet.";
    }
    leaf reply-mode {
      type vxlan-reply-mode;
      default "udp";
      description
        "Mode for responding to test packets in a test.";
    }
    leaf probe-count {
      type uint32 {
        range "1..15";
      }
      default "3";
      description
        "Number of packets.";
    }
    leaf interval {
      type uint32 {
        range "1..60";
      }
      units "s";
      default "4";
      description
        "Interval for sending packets.";
    }
    leaf timeout {
      type uint32 {
        range "1..60";
      }
      units "s";
      default "3";
      description
        "Time to wait for a response packet after a test packet is sent.";
    }
    leaf tos {
      type uint16 {
        range "0..255";
      }
      default "0";
      description
        "TOS.";
    }
    leaf lb-vxlan-source-port-begin {
      type uint16 {
        range "49152..65535";
      }
      must 'not(../lb-source-address) and not(../lb-destination-address) and not(../lb-protocol) and not(../lb-source-port) and not(../lb-destination-port) and not(../lb-source-mac) and not(../lb-destination-mac)';
      description
        "VXLAN begin source port for load balance.";
    }
    leaf lb-vxlan-source-port-end {
      type uint16 {
        range "49152..65535";
      }
      must 'not(../lb-source-address) and not(../lb-destination-address) and not(../lb-protocol) and not(../lb-source-port) and not(../lb-destination-port) and not(../lb-source-mac) and not(../lb-destination-mac)';
      description
        "VXLAN end source port for load balance.";
    }
    leaf lb-source-address {
      type inet:ipv4-address-no-zone;
      must '../lb-destination-address and ../lb-protocol and ../lb-source-port and ../lb-destination-port and ../lb-source-mac and ../lb-destination-mac and not(../lb-vxlan-source-port-begin) and not(../lb-vxlan-source-port-end)';
      description
        "The source address of the user packet for load balance.";
    }
    leaf lb-destination-address {
      type inet:ipv4-address-no-zone;
      must '../lb-source-address and ../lb-protocol and ../lb-source-port and ../lb-destination-port and ../lb-source-mac and ../lb-destination-mac and not(../lb-vxlan-source-port-begin) and not(../lb-vxlan-source-port-end)';
      description
        "The destination address of the user packet for load balance.";
    }
    leaf lb-protocol {
      type uint8 {
        range "0..255";
      }
      must '../lb-destination-address and ../lb-source-address and ../lb-source-port and ../lb-destination-port and ../lb-source-mac and ../lb-destination-mac and not(../lb-vxlan-source-port-begin) and not(../lb-vxlan-source-port-end)';
      description
        "The protocol of the user packet for load balance.";
    }
    leaf lb-source-port {
      type uint16 {
        range "0..65535";
      }
      must '../lb-destination-address and ../lb-protocol and ../lb-source-address and ../lb-destination-port and ../lb-source-mac and ../lb-destination-mac and not(../lb-vxlan-source-port-begin) and not(../lb-vxlan-source-port-end)';
      description
        "The source port of the user packet for load balance.";
    }
    leaf lb-destination-port {
      type uint16 {
        range "0..65535";
      }
      must '../lb-destination-address and ../lb-protocol and ../lb-source-port and ../lb-source-address and ../lb-source-mac and ../lb-destination-mac and not(../lb-vxlan-source-port-begin) and not(../lb-vxlan-source-port-end)';
      description
        "The destination port of the user packet for load balance.";
    }
    leaf lb-source-mac {
      type pub-type:mac-address;
      must '../lb-destination-address and ../lb-protocol and ../lb-source-port and ../lb-destination-port and ../lb-source-address and ../lb-destination-mac and not(../lb-vxlan-source-port-begin) and not(../lb-vxlan-source-port-end)';
      description
        "The source MAC of the user packet for load balance.";
    }
    leaf lb-destination-mac {
      type pub-type:mac-address;
      must '../lb-destination-address and ../lb-protocol and ../lb-source-port and ../lb-destination-port and ../lb-source-address and ../lb-source-address and not(../lb-vxlan-source-port-begin) and not(../lb-vxlan-source-port-end)';
      description
        "The destination MAC of the user packet for load balance.";
    }
    leaf frequency {
      type uint32 {
        range "1..604800";
      }
      description
        "Result record number of test instance.";
    }
    leaf result-num {
      type uint32 {
        range "1..10";
      }
      default "5";
      description
        "History record number of test instance.";
    }
    leaf history-num {
      type uint32 {
        range "0..1000";
      }
      default "60";
      description
        "Description of test instance.";
    }
    leaf description {
      type string {
        length "1..230";
      }
      description
        "Aging time of test instance.";
    }
    leaf age-time {
      type pub-type:time;
      default "00:00:00";
      description
        "Aging time of test instance.";
    }
  }

  grouping lspping-intance-input {
    description
      "Lsp ping test intance input parameters.";
    choice lsp-protocol {
      description
        "The test-type of LSP.";
      case ip {
        description
          "The test-type of LSP is ldp.";
        container ldp-lsp-ping {
          description
            "Container of ldp lsp ping.";
          leaf dest-address {
            type inet:ipv4-address-no-zone;
            description
              "Destination IP address.";
          }
          leaf mask-len {
            type uint8 {
              range "0..32";
            }
            description
              "LSP IPv4 address prefix mask length.";
          }
          leaf loopback-address {
            type inet:ipv4-address-no-zone;
            description
              "The IP address of the 127.0.0.0/8 network segment in the LSP ping message header.";
          }
          leaf next-hop {
            type inet:ipv4-address-no-zone;
            description
              "Nexthop address.";
          }
          leaf data-fill {
            type string {
              length "1..230";
            }
            description
              "Data padding.";
          }
          leaf reply-mode {
            type ip-lsp-reply-mode-type;
            default "udp";
            description
              "LSP reply mode.";
          }
        }
      }
      case bgp {
        description
          "The test-type of LSP is bgp.";
        container bgp-lsp-ping {
          description
            "Container of bgp lsp ping.";
          leaf dest-address {
            type inet:ipv4-address-no-zone;
            description
              "Destination IP address.";
          }
          leaf mask-len {
            type uint8 {
              range "0..32";
            }
            description
              "LSP IPv4 address prefix mask length.";
          }
          leaf loopback-address {
            type inet:ipv4-address-no-zone;
            description
              "The IP address of the 127.0.0.0/8 network segment in the LSP ping message header.";
          }
          leaf next-hop {
            type inet:ipv4-address-no-zone;
            description
              "Nexthop address.";
          }
          leaf data-fill {
            type string {
              length "1..230";
            }
            description
              "Data padding.";
          }
          leaf reply-mode {
            type ip-lsp-reply-mode-type;
            default "udp";
            description
              "LSP reply mode.";
          }
        }
      }
      case te {
        description
          "The test-type of LSP is te.";
        container te-lsp-ping {
          description
            "Container of te lsp ping.";
          leaf tunnel-name {
            type leafref {
              path "/ifm:ifm/ifm:interfaces/ifm:interface/ifm:name";
            }
            description
              "TE tunnel name.";
          }
          leaf lsp-path {
            type lsp-path;
            description
              "Lsp path.";
          }
          leaf data-fill {
            type string {
              length "1..230";
            }
            description
              "Data padding.";
          }
          leaf reply-mode {
            type lsp-reply-mode-type;
            default "udp";
            description
              "LSP reply mode.";
          }
        }
      }
      case sr-te {
        description
          "The test-type of LSP is sr-te.";
        container sr-te-lsp-ping {
          description
            "Container of sr-te lsp ping.";
          leaf tunnel-name {
            type leafref {
              path "/ifm:ifm/ifm:interfaces/ifm:interface/ifm:name";
            }
            description
              "TE tunnel name.";
          }
          leaf lsp-path {
            type lsp-path;
            description
              "Lsp path.";
          }
          leaf data-fill {
            type string {
              length "1..230";
            }
            description
              "Data padding.";
          }
          leaf reply-mode {
            type srte-lsp-reply-mode-type;
            default "udp";
            description
              "LSP reply mode.";
          }
        }
      }
      case sr-be {
        description
          "The test-type of LSP is sr-be.";
        container sr-be-lsp-ping {
          description
            "Container of sr-be lsp ping.";
          leaf dest-address {
            type inet:ipv4-address-no-zone;
            description
              "Destination IP address.";
          }
          leaf mask-len {
            type uint8 {
              range "0..32";
            }
            description
              "LSP IPv4 address prefix mask length.";
          }
          choice remote-fec {
            description
              "Remote FEC type.";
            case ldp {
              description
                "Remote FEC LDP.";
              container remote-fec-ldp {
                description
                  "Remote FEC LDP.";
                leaf remote-mask-len {
                  type uint8 {
                    range "0..32";
                  }
                  default "0";
                  description
                    "Remote FEC mask length.";
                }
                leaf remote-fec-ip-address {
                  type inet:ipv4-address-no-zone;
                  description
                    "Remote FEC IPv4 address.";
                }
              }
            }
          }
        }
      }
      case srte-policy {
        description
          "The test-type of LSP is srte-policy.";
        container srte-policy-lsp-ping {
          description
            "Container of srte-policy lsp ping.";
          leaf policy-name {
            type string {
              length "1..31";
            }
            must 'not(../color or ../endpoint-ip) and not(../binding-sid)';
            description
              "SRTE policy name.";
          }
          leaf endpoint-ip {
            type inet:ipv4-address-no-zone;
            must 'not(../policy-name) and not(../endpoint-ip) and ../color';
            description
              "Endpoint IP address.";
          }
          leaf color {
            type uint32 {
              range "1..4294967295";
            }
            must 'not(../policy-name) and not(../binding-sid) and ../endpoint-ip';
            description
              "Endpoint color ID.";
          }
          leaf binding-sid {
            type uint32 {
              range "16..1048575";
            }
            must 'not(../policy-name) and not(../color or ../endpoint-ip)';
            description
              "Binding segmentlist ID.";
          }
        }
      }
    }
    leaf timeout {
      type uint32 {
        range "1..60";
      }
      units "s";
      default "3";
      description
        "Time to wait for a response packet after test packets are sent.";
    }
    leaf frag-flag {
      type boolean;
      default "false";
      description
        "Use fragment to send packets.";
    }
    leaf source-address {
      type inet:ipv4-address-no-zone;
      description
        "Source IP address.";
    }
    leaf exp {
      type uint8 {
        range "0..7";
      }
      default "0";
      description
        "Configures the LSP exp value.";
    }
    leaf ttl {
      type uint8 {
        range "1..255";
      }
      default "30";
      description
        "TTL value of NQA test packets.";
    }
    leaf interval {
      type uint32 {
        range "1..60";
      }
      units "s";
      default "4";
      description
        "Interval for sending packets.";
    }
    leaf probe-count {
      type uint32 {
        range "1..15";
      }
      default "3";
      description
        "Number of sent packets.";
    }
    leaf data-size {
      type uint32 {
        range "0..9600";
      }
      default "0";
      description
        "Packet size (byte).";
    }
    leaf fail-percent {
      type uint32 {
        range "1..100";
      }
      default "100";
      description
        "The rate of loss (%) that the test case performed successfully.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping lsptrace-intance-input {
    description
      "Lsp trace test intance input parameters.";
    choice lsp-protocol {
      description
        "The test-type of LSP.";
      case ipv4 {
        description
          "The test-type of LSP is ldp.";
        container ldp-lsp-trace {
          description
            "Container of ldp lsp trace.";
          leaf dest-address {
            type inet:ipv4-address-no-zone;
            description
              "Destination IP address.";
          }
          leaf mask-len {
            type uint8 {
              range "0..32";
            }
            description
              "LSP IPv4 address prefix mask length.";
          }
          leaf loopback-address {
            type inet:ipv4-address-no-zone;
            description
              "The IP address of the 127.0.0.0/8 network segment in the LSP trace message header.";
          }
          leaf reply-mode {
            type ip-lsp-reply-mode-type;
            default "udp";
            description
              "LSP reply mode.";
          }
        }
      }
      case bgp {
        description
          "The test-type of LSP is bgp.";
        container bgp-lsp-trace {
          description
            "Container of bgp lsp trace.";
          leaf dest-address {
            type inet:ipv4-address-no-zone;
            description
              "Destination IP address.";
          }
          leaf mask-len {
            type uint8 {
              range "0..32";
            }
            description
              "LSP IPv4 address prefix mask length.";
          }
          leaf loopback-address {
            type inet:ipv4-address-no-zone;
            description
              "The IP address of the 127.0.0.0/8 network segment in the LSP trace message header.";
          }
          leaf reply-mode {
            type ip-lsp-reply-mode-type;
            default "udp";
            description
              "LSP reply mode.";
          }
        }
      }
      case te {
        description
          "The test-type of LSP is te.";
        container te-lsp-trace {
          description
            "Container of te lsp trace.";
          leaf tunnel-name {
            type leafref {
              path "/ifm:ifm/ifm:interfaces/ifm:interface/ifm:name";
            }
            description
              "TE tunnel name.";
          }
          leaf lsp-path {
            type lsp-path;
            description
              "Lsp path.";
          }
          leaf reply-mode {
            type lsp-reply-mode-type;
            default "udp";
            description
              "LSP reply mode.";
          }
        }
      }
      case sr-te {
        description
          "The test-type of LSP is sr-te.";
        container sr-te-lsp-trace {
          description
            "Container of sr-te lsp trace.";
          leaf tunnel-name {
            type leafref {
              path "/ifm:ifm/ifm:interfaces/ifm:interface/ifm:name";
            }
            description
              "TE tunnel name.";
          }
          leaf lsp-path {
            type lsp-path;
            description
              "Lsp path.";
          }
          leaf reply-mode {
            type srte-lsp-reply-mode-type;
            default "udp";
            description
              "LSP reply mode.";
          }
        }
      }
      case sr-be {
        description
          "The test-type of LSP is sr-be.";
        container sr-be-lsp-trace {
          description
            "Container of sr-be lsp trace.";
          leaf dest-address {
            type inet:ipv4-address-no-zone;
            description
              "Destination IP address.";
          }
          leaf mask-len {
            type uint8 {
              range "0..32";
            }
            description
              "LSP IPv4 address prefix mask length.";
          }
          choice remote-fec {
            description
              "Remote FEC type.";
            case ldp {
              description
                "Remote FEC LDP.";
              container remote-fec-ldp {
                description
                  "Remote FEC LDP.";
                leaf remote-mask-len {
                  type uint8 {
                    range "0..32";
                  }
                  default "0";
                  description
                    "Remote FEC mask length.";
                }
                leaf remote-fec-ip-address {
                  type inet:ipv4-address-no-zone;
                  description
                    "Remote FEC IPv4 address.";
                }
              }
            }
          }
        }
      }
      case srte-policy {
        description
          "The test-type of LSP is srte-policy.";
        container srte-policy-lsp-trace {
          description
            "Container of srte-policy lsp trace.";
          leaf policy-name {
            type string {
              length "1..31";
            }
            must 'not(../color or ../endpoint-ip) and not(../binding-sid)';
            description
              "SRTE policy name.";
          }
          leaf endpoint-ip {
            type inet:ipv4-address-no-zone;
            must 'not(../policy-name) and not(../endpoint-ip) and ../color';
            description
              "Endpoint IP address.";
          }
          leaf color {
            type uint32 {
              range "1..4294967295";
            }
            must 'not(../policy-name) and not(../binding-sid) and ../endpoint-ip';
            description
              "Endpoint color ID.";
          }
          leaf binding-sid {
            type uint32 {
              range "16..1048575";
            }
            must 'not(../policy-name) and not(../color or ../endpoint-ip)';
            description
              "Binding segmentlist ID.";
          }
        }
      }
    }
    leaf frag-flag {
      type boolean;
      default "false";
      description
        "Use fragment to send packets.";
    }
    leaf exp {
      type uint8 {
        range "0..7";
      }
      default "0";
      description
        "Configures the LSP exp value.";
    }
    leaf probe-count {
      type uint32 {
        range "1..15";
      }
      default "3";
      description
        "Number of sent packets.";
    }
    leaf source-address {
      type inet:ipv4-address-no-zone;
      description
        "Source IP address.";
    }
    leaf first-ttl {
      type uint8 {
        range "1..255";
      }
      must '../first-ttl<=../max-ttl';
      default "1";
      description
        "Packet first TTL.";
    }
    leaf max-ttl {
      type uint8 {
        range "1..255";
      }
      must '../first-ttl<=../max-ttl';
      default "30";
      description
        "Packet maximum TTL.";
    }
    leaf timeout {
      type uint32 {
        range "1..60";
      }
      units "s";
      default "3";
      description
        "Time to wait for a response packet after a test packet is sent.";
    }
    leaf hop-fail-times {
      type uint8 {
        range "1..255";
      }
      default "5";
      description
        "The times of hop failure.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      must '(../frequency>=60)';
      description
        "Test instance frequency (s).";
    }
  }

  grouping lsp-jitter-intance-input {
    description
      "Lsp jitter test intance input parameters.";
    choice lsp-protocol {
      description
        "The test-type of LSP.";
      case ipv4 {
        description
          "The test-type of LSP is LDP.";
        container ldp-lsp-jitter {
          description
            "Container of ldp jitter instance.";
          leaf dest-address {
            type inet:ipv4-address-no-zone;
            description
              "Destination IP address. (Must specify the destination address to start the test)";
          }
          leaf mask-len {
            when '../dest-address';
            type uint8 {
              range "0..32";
            }
            must '../dest-address';
            default "0";
            description
              "LSP IPv4 address prefix mask length.";
          }
          leaf loopback-address {
            type inet:ipv4-address-no-zone;
            must '../dest-address';
            description
              "The IP address of the 127.0.0.0/8 network segment in the LSP jitter message header.";
          }
          leaf reply-mode {
            type ip-lsp-reply-mode-type;
            default "udp";
            description
              "LSP reply mode.";
          }
        }
      }
      case te {
        description
          "The test-type of LSP is TE.";
        container te-lsp-jitter {
          presence "Present enable te jitter test intance input.";
          description
            "Container of te jitter instance.";
          leaf tunnel-name {
            type leafref {
              path "/ifm:ifm/ifm:interfaces/ifm:interface/ifm:name";
            }
            description
              "TE tunnel name.";
          }
          leaf lsp-path {
            type lsp-path;
            default "working";
            description
              "Lsp path.";
          }
          leaf reply-mode {
            type lsp-reply-mode-type;
            default "udp";
            description
              "LSP reply mode.";
          }
        }
      }
    }
    leaf timeout {
      type uint32 {
        range "1..60";
      }
      units "s";
      default "3";
      description
        "Time to wait for a response packet after a test packet is sent.";
    }
    leaf frag-flag {
      type boolean;
      default "false";
      description
        "Use fragment to send packets.";
    }
    leaf source-address {
      type inet:ipv4-address-no-zone;
      description
        "Source IP address.";
    }
    leaf exp {
      type uint8 {
        range "0..7";
      }
      default "0";
      description
        "Configures the LSP exp value.";
    }
    leaf ttl {
      type uint8 {
        range "1..255";
      }
      default "30";
      description
        "TTL value of NQA test packets.";
    }
    leaf interval {
      type uint32 {
        range "1..60";
      }
      units "s";
      default "1";
      description
        "Interval for sending packets.";
    }
    leaf probe-count {
      type uint32 {
        range "1..15";
      }
      default "3";
      description
        "Number of probes.";
    }
    leaf jitter-packet-num {
      type uint32 {
        range "1..3000";
      }
      default "20";
      description
        "Number of sent packets.";
    }
    leaf data-size {
      type uint32 {
        range "0..9600";
      }
      units "Byte";
      default "0";
      description
        "Packet size.";
    }
    leaf data-fill {
      type string {
        length "1..230";
      }
      description
        "Data padding.";
    }
    leaf fail-percent {
      type uint32 {
        range "1..100";
      }
      units "%";
      default "100";
      description
        "The rate of loss that the test case performed successfully.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping pwe3-ping-intance-input {
    description
      "Pwe3 ping test intance input parameters.";
    leaf vc-type {
      type vc-type;
      default "ldp";
      description
        "VC TYPE.";
    }
    leaf local-pw-type {
      type pw-type;
      default "ethernet";
      description
        "Local PW type.";
    }
    leaf local-pw-id {
      type uint32 {
        range "1..4294967295";
      }
      description
        "Local PW ID.";
    }
    leaf label-type {
      type pwe3-label-type;
      default "control-word";
      description
        "Label type.";
    }
    leaf remote-pw-id {
      type uint32 {
        range "1..4294967295";
      }
      description
        "Remote PW ID.";
    }
    leaf dest-address {
      type inet:ipv4-address-no-zone;
      description
        "Destination IP address. (Must specify the destination address to start the test)";
    }
    leaf timeout {
      type uint32 {
        range "1..60";
      }
      units "s";
      default "3";
      description
        "Time to wait for a response packet after a test packet is sent.";
    }
    leaf max-ttl {
      type uint8 {
        range "1..255";
      }
      default "30";
      description
        "Packet maximum TTL.";
    }
    leaf exp {
      type uint8 {
        range "0..7";
      }
      default "0";
      description
        "Configures the Pwe3Ping exp value.";
    }
    leaf reply-mode {
      type lsp-reply-mode-type;
      must "((../reply-mode='no-reply' or ../reply-mode='udp' or ../reply-mode='level-control-channel') )";
      default "udp";
      description
        "Pwe3Ping reply mode.";
    }
    leaf interval {
      type uint32 {
        range "1..60";
      }
      units "s";
      default "4";
      description
        "Set interval time between two packets.";
    }
    leaf probe-count {
      type uint32 {
        range "1..15";
      }
      default "3";
      description
        "Number of sent packets.";
    }
    leaf data-size {
      type uint32 {
        range "0..9600";
      }
      default "0";
      description
        "Specify NQA test packets size.";
    }
    leaf data-fill {
      type string {
        length "1..230";
      }
      description
        "Specify NQA test packets payload string.";
    }
    leaf fail-percent {
      type uint32 {
        range "1..100";
      }
      default "100";
      description
        "Set NQA test fail percent.";
    }
    leaf probe-failtimes {
      type uint32 {
        range "1..15";
      }
      default "1";
      description
        "Packet failed threshold determining whether send traps or events.";
    }
    leaf test-failtimes {
      type uint32 {
        range "1..15";
      }
      default "1";
      description
        "Test failed threshold determining whether send traps or events.";
    }
    leaf threshold-rtd {
      type uint32 {
        range "1..60000";
      }
      description
        "RTD threshold.";
    }
    uses send-trap-enable;
    leaf sender-address {
      type inet:ipv4-address-no-zone;
      description
        "Set the source address of the targeted session.";
    }
    leaf no-cw-flag {
      type boolean;
      must "../label-type and ../label-type!='control-word'";
      default "false";
      description
        "NO control word.";
    }
    leaf ttl-mode {
      type ttl-mode;
      default "uniform";
      description
        "TTL mode.";
    }
    leaf frag-flag {
      type boolean;
      default "false";
      description
        "Use fragment to send packets.";
    }
    leaf peer-address {
      type inet:ipv4-address-no-zone;
      description
        "Peer IP Address.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping pwe3-trace-intance-input {
    description
      "Pwe3 trace test intance input parameters.";
    leaf vc-type {
      type vc-type;
      default "ldp";
      description
        "VC TYPE.";
    }
    leaf local-pw-type {
      type pw-type;
      default "ethernet";
      description
        "Local PW type.";
    }
    leaf local-pw-id {
      type uint32 {
        range "1..4294967295";
      }
      description
        "Local PW ID.";
    }
    leaf label-type {
      type pwe3-label-type;
      default "control-word";
      description
        "Label type.";
    }
    leaf remote-pw-id {
      type uint32 {
        range "1..4294967295";
      }
      must "../lsp-version!='rfc4379'";
      description
        "Remote PW ID.";
    }
    leaf dest-address {
      type inet:ipv4-address-no-zone;
      description
        "Destination IP address. (Must specify the destination address to start the test)";
    }
    leaf timeout {
      type uint32 {
        range "1..60";
      }
      units "s";
      default "3";
      description
        "Time to wait for a response packet after a test packet is sent.";
    }
    leaf first-ttl {
      type uint8 {
        range "1..255";
      }
      must "(../first-ttl <= ../max-ttl)";
      default "1";
      description
        "Packet first TTL.";
    }
    leaf max-ttl {
      type uint8 {
        range "1..255";
      }
      must "(../max-ttl > ../first-ttl)";
      default "30";
      description
        "Packet maximum TTL.";
    }
    leaf exp {
      type uint8 {
        range "0..7";
      }
      default "0";
      description
        "Configures the Pwe3Trace exp value.";
    }
    leaf reply-mode {
      type lsp-reply-mode-type;
      default "udp";
      description
        "Pwe3Trace reply mode.";
    }
    leaf packet-count {
      type uint32 {
        range "1..15";
      }
      units "packet";
      default "3";
      description
        "Number of sent packets.";
    }
    leaf probe-failtimes {
      type uint32 {
        range "1..15";
      }
      default "1";
      description
        "Packet failed threshold determining whether send traps or events.";
    }
    leaf test-failtimes {
      type uint32 {
        range "1..15";
      }
      default "1";
      description
        "Test failed threshold determining whether send traps or events.";
    }
    leaf lsp-version {
      type lsp-version;
      default "rfc4379";
      description
        "Lsp version.";
    }
    leaf threshold-rtd {
      type uint32 {
        range "1..60000";
      }
      description
        "RTD threshold.";
    }
    leaf send-trap-bits {
      type bits {
        bit rtd {
          position 28;
          description
            "Indicates that a trap is sent when the RTD exceeds the threshold.";
        }
        bit testcomplete {
          position 29;
          description
            "Indicates that a trap is sent when a test succeeds.";
        }
        bit testfailure {
          position 30;
          description
            "Indicates that a trap is sent when the number of test failures reaches the threshold.";
        }
        bit probefailure {
          position 31;
          description
            "Indicates that a trap is sent when the OWD from the source to the
             destination exceeds the threshold.
             This parameter applies only to jitter test instances.";
        }
      }
      description
        "Configures conditions for sending traps.";
    }
    leaf ttl-mode {
      type ttl-mode;
      default "uniform";
      description
        "TTL mode.";
    }
    leaf hop-fail-times {
      type uint8 {
        range "1..255";
      }
      default "5";
      description
        "The times of hop failure.";
    }
    leaf frag-flag {
      type boolean;
      default "false";
      description
        "Use fragment to send packets.";
    }
    leaf peer-address {
      type inet:ipv4-address-no-zone;
      description
        "Peer IP Address.";
    }
    leaf no-cw-flag {
      when "../label-type!='control-word'";
      type boolean;
      default "false";
      description
        "NO control word.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      units "s";
      description
        "Test instance frequency. The frequency must be greater than the value of the following formula; otherwise, the test results may be inaccurate:
         (Number of sent Packets - 1) * (Packet sending interval) + (Timeout period).";
    }
  }

  grouping vpls-pw-ping-intance-input {
    description
      "Vpls pw ping test intance input parameters.";
    leaf vsi-name {
      type string {
        length "1..31";
      }
      description
        "Vsi name.";
    }
    leaf peer-address {
      type inet:ipv4-address-no-zone;
      description
        "Peer IP address.";
    }
    leaf vc-type {
      type vc-type;
      default "ldp";
      description
        "VC type.";
    }
    leaf local-pw-id {
      type uint32 {
        range "1..4294967295";
      }
      description
        "Local PW id.";
    }
    leaf remote-pw-id {
      type uint32 {
        range "1..4294967295";
      }
      description
        "Remote PW id.";
    }
    leaf remote-address {
      type inet:ipv4-address-no-zone;
      description
        "Remote address.";
    }
    leaf label-type {
      type pwe3-label-type;
      default "label-alert";
      description
        "Label type.";
    }
    leaf timeout {
      type uint32 {
        range "1..60";
      }
      units "s";
      default "3";
      description
        "Time to wait for a response packet after a test packet is sent.";
    }
    leaf max-ttl {
      type uint8 {
        range "1..255";
      }
      default "30";
      description
        "Time to live.";
    }
    leaf exp {
      type uint8 {
        range "0..7";
      }
      default "0";
      description
        "Exp value.";
    }
    leaf reply-mode {
      type lsp-reply-mode-type;
      must "((../reply-mode='no-reply' or ../reply-mode='udp' or ../reply-mode='level-control-channel') )";
      default "udp";
      description
        "Mode for responding to test packets in a test.";
    }
    leaf interval {
      type uint32 {
        range "1..60";
      }
      units "s";
      default "4";
      description
        "Interval for sending packets.";
    }
    leaf probe-count {
      type uint32 {
        range "1..15";
      }
      default "3";
      description
        "Number of probes.";
    }
    leaf data-size {
      type uint32 {
        range "0..9600";
      }
      default "0";
      description
        "Packet size (byte).";
    }
    leaf data-fill {
      type string {
        length "1..230";
      }
      description
        "Packing string.";
    }
    leaf fail-percent {
      type uint32 {
        range "1..100";
      }
      default "100";
      description
        "Loss ratio (%), determining whether the test is sucessful.";
    }
    leaf probe-failtimes {
      type uint32 {
        range "1..15";
      }
      default "1";
      description
        "Packet failed threshold determining whether send traps or events.";
    }
    leaf test-failtimes {
      type uint32 {
        range "1..15";
      }
      default "1";
      description
        "Test failed threshold determining whether send traps or events.";
    }
    leaf threshold-rtd {
      type uint32 {
        range "1..60000";
      }
      description
        "Round trip delay time threshold value.";
    }
    uses send-trap-enable;
    leaf sender-address {
      type inet:ipv4-address-no-zone;
      description
        "Sender address.";
    }
    leaf no-cw-flag {
      type boolean;
      default "false";
      description
        "No control-word flag.";
    }
    leaf frag-flag {
      type boolean;
      default "false";
      description
        "Use fragment to send packets.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping vpls-pw-trace-intance-input {
    description
      "Vpls pw trace test intance input parameters.";
    leaf vsi-name {
      type string {
        length "1..31";
      }
      description
        "Vsi name.";
    }
    leaf peer-address {
      type inet:ipv4-address-no-zone;
      description
        "Peer address.";
    }
    leaf vc-type {
      type vc-type;
      default "ldp";
      description
        "VC type.";
    }
    leaf local-pw-id {
      type uint32 {
        range "1..4294967295";
      }
      description
        "Local PW id.";
    }
    leaf label-type {
      type pwe3-label-type;
      default "label-alert";
      description
        "Label type.";
    }
    leaf timeout {
      type uint32 {
        range "1..60";
      }
      units "s";
      default "3";
      description
        "Time to wait for a response packet after a test packet is sent.";
    }
    leaf first-ttl {
      type uint8 {
        range "1..255";
      }
      default "1";
      description
        "Packet first TTL.";
    }
    leaf max-ttl {
      type uint8 {
        range "1..255";
      }
      default "30";
      description
        "Time to live.";
    }
    leaf exp {
      type uint8 {
        range "0..7";
      }
      default "0";
      description
        "Exp value.";
    }
    leaf reply-mode {
      type lsp-reply-mode-type;
      must "((../reply-mode='no-reply' or ../reply-mode='udp' or ../reply-mode='level-control-channel') )";
      default "udp";
      description
        "Mode for responding to test packets in a test.";
    }
    leaf probe-count {
      type uint32 {
        range "1..15";
      }
      default "3";
      description
        "Number of probes.";
    }
    leaf probe-failtimes {
      type uint32 {
        range "1..15";
      }
      default "1";
      description
        "Packet failed threshold determining whether send traps or events.";
    }
    leaf test-failtimes {
      type uint32 {
        range "1..15";
      }
      default "1";
      description
        "Test failed threshold determining whether send traps or events.";
    }
    leaf threshold-rtd {
      type uint32 {
        range "1..60000";
      }
      description
        "Round trip delay time threshold value.";
    }
    uses send-trap-enable;
    leaf no-cw-flag {
      type boolean;
      default "false";
      description
        "No control-word flag.";
    }
    leaf full-display-flag {
      type boolean;
      default "false";
      description
        "Full path display flag.";
    }
    leaf ttl-mode {
      type ttl-mode;
      default "uniform";
      description
        "TTL mode.";
    }
    leaf hop-fail-times {
      type uint8 {
        range "1..255";
      }
      default "5";
      description
        "The times of hop failure.";
    }
    leaf frag-flag {
      type boolean;
      default "false";
      description
        "Use fragment to send packets.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping vpls-mac-ping-intance-input {
    description
      "Vpls mac ping test intance input parameters.";
    leaf vsi {
      type string {
        length "1..32";
      }
      description
        "Vsi name.";
    }
    leaf dest-mac-address {
      type pub-type:mac-address;
      description
        "Destination MAC address.";
    }
    leaf vlan {
      type uint16 {
        range "1..4094";
      }
      description
        "VLAN.";
    }
    leaf data-fill {
      type string {
        length "1..231";
      }
      description
        "Message data padding.";
    }
    leaf data-size {
      type uint16 {
        range "100..1442";
      }
      default "100";
      description
        "Packet size (byte).";
    }
    leaf exp {
      type uint8 {
        range "0..7";
      }
      default "0";
      description
        "Exp value.";
    }
    leaf reply-mode {
      type vpls-reply-mode-type;
      default "udp";
      description
        "Mode for responding to test packets in a test.";
    }
    leaf ttl {
      type uint8 {
        range "1..255";
      }
      default "30";
      description
        "Time to live.";
    }
    leaf interval {
      type uint32 {
        range "1..60";
      }
      units "s";
      default "4";
      description
        "Interval for sending packets.";
    }
    leaf fail-percent {
      type uint32 {
        range "1..100";
      }
      default "100";
      description
        "Fail Percent.";
    }
    leaf test-fails {
      type uint32 {
        range "1..15";
      }
      default "1";
      description
        "Test failed threshold determining whether send traps or events.";
    }
    leaf probe-fails {
      type uint32 {
        range "1..15";
      }
      default "1";
      description
        "Packet failed threshold determining whether send traps or events.";
    }
    leaf threshold-rtd {
      type uint32 {
        range "1..60000";
      }
      description
        "Round trip delay time threshold value.";
    }
    uses send-trap-enable;
    leaf probe-count {
      type uint32 {
        range "1..15";
      }
      default "3";
      description
        "Packet Count.";
    }
    leaf timeout {
      type uint32 {
        range "1..60";
      }
      units "s";
      default "3";
      description
        "Time to wait for a response packet after a test packet is sent.";
    }
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s). The frequency must be greater than the value of the following formula; otherwise, the test results may be inaccurate:
         (Number of sent Packets - 1) * (Packet sending interval) + (Timeout period).";
    }
  }

  grouping mac-ping-intance-input {
    description
      "Mac ping test intance input parameters.";
    leaf dest-mac-address {
      type pub-type:mac-address;
      description
        "Destination MAC address.";
    }
    leaf remote-mep-id {
      type uint16 {
        range "1..8191";
      }
      description
        "Remote MEP ID.";
    }
    leaf mep-id {
      type uint16 {
        range "1..8191";
      }
      description
        "Local MEP ID.";
    }
    leaf md-name {
      type string {
        length "1..44";
      }
      description
        "Name of MD domain.";
    }
    leaf ma-name {
      type string {
        length "1..44";
      }
      description
        "Name of MA domain.";
    }
    leaf probe-count {
      type uint32 {
        range "1..15";
      }
      default "3";
      description
        "Number of probes.";
    }
    leaf jitter-packet-num {
      type uint32 {
        range "1..3000";
      }
      default "1";
      description
        "Number of packets.";
    }
    leaf data-size {
      type uint16 {
        range "64..2000";
      }
      default "95";
      description
        "Packet size (byte).";
    }
    leaf timeout {
      type uint32 {
        range "1..60";
      }
      units "s";
      default "3";
      description
        "Time to wait for a response packet after a test packet is sent.";
    }
    leaf interval {
      type uint32 {
        range "1..60";
      }
      units "s";
      default "4";
      description
        "Interval for sending packets.";
    }
    leaf out-if-name {
      type leafref {
        path "/ifm:ifm/ifm:interfaces/ifm:interface/ifm:name";
      }
      description
        "Out interface name.";
    }
    leaf fail-percent {
      type uint32 {
        range "1..100";
      }
      default "100";
      description
        "Loss ratio (%), determining whether the test is sucessful.";
    }
    leaf test-fails {
      type uint32 {
        range "1..15";
      }
      default "1";
      description
        "Test failed threshold determining whether send traps or events.";
    }
    leaf probe-fails {
      type uint32 {
        range "1..15";
      }
      default "1";
      description
        "Packet failed threshold determining whether send traps or events.";
    }
    leaf threshold-rtd {
      type uint32 {
        range "1..60000";
      }
      description
        "Round trip delay time threshold value.";
    }
    uses send-trap-enable;
    leaf result-num {
      type uint32 {
        range "1..10";
      }
      default "5";
      description
        "Result record number of test instance.";
    }
    leaf history-num {
      type uint32 {
        range "0..1000";
      }
      default "60";
      description
        "History record number of test instance.";
    }
    leaf description {
      type string {
        length "1..230";
      }
      description
        "Description of test instance.";
    }
    leaf age-time {
      type pub-type:time;
      default "00:00:00";
      description
        "Aging time of test instance.";
    }
    leaf frequency {
      type uint32 {
        range "1..604800";
      }
      description
        "Test instance frequency (s).";
    }
  }

  grouping general-flow-intance-input {
    description
      "General flow test intance input parameters.";
    leaf measure {
      type test-measure-type;
      description
        "Test mode.";
    }
    leaf dest-address {
      type inet:ipv4-address-no-zone;
      description
        "Destination IP address.";
    }
    leaf dest-mac-address {
      type pub-type:mac-address;
      description
        "Destination MAC address.";
    }
    leaf source-address {
      type inet:ipv4-address-no-zone;
      must '../dest-address or (not(../dest-address) and not(../source-address))';
      description
        "Source IP address.";
    }
    leaf source-mac-address {
      type pub-type:mac-address;
      description
        "Source MAC address.";
    }
    leaf source-if-name {
      type leafref {
        path "/ifm:ifm/ifm:interfaces/ifm:interface/ifm:name";
      }
      must '../dest-address or (not(../dest-address) and not(../source-if-name))';
      description
        "Source interface name.";
    }
    leaf fwd-simu-if-name {
      type leafref {
        path "/ifm:ifm/ifm:interfaces/ifm:interface/ifm:name";
      }
      description
        "Forwarding-simulation inbound interface.";
    }
    leaf share-mode-enable {
      type boolean;
      must "(../fwd-simu-if-name and ../share-mode-enable='true') or (../share-mode-enable='false')";
      description
        "Enable share mode.";
    }
    leaf duration {
      type uint32 {
        range "10..172800";
      }
      default "60";
      description
        "Test duration time.";
    }
    leaf data-size-list {
      type string {
        length "1..50";
      }
      default "64 128 256 512 1024 1280 1518";
      description
        "Packet size value (byte).";
    }
    leaf tos {
      type uint16 {
        range "0..255";
      }
      must '../dest-address or (not(../dest-address) and ../tos=0)';
      default "0";
      description
        "ToS.";
    }
    leaf rate-low {
      type uint32 {
        range "1..100000000";
      }
      description
        "Lower limit of the rate.";
    }
    leaf rate-high {
      type uint32 {
        range "1..100000000";
      }
      description
        "Upper limit of the rate.";
    }
    leaf ce-vlan {
      type uint16 {
        range "1..4094";
      }
      description
        "PE VLAN ID.";
    }
    leaf pe-vlan {
      type uint16 {
        range "1..4094";
      }
      description
        "CE VLAN ID.";
    }
    leaf interval {
      type uint32 {
        range "1..60";
      }
      units "s";
      default "4";
      description
        "Interval for sending packets.";
    }
    leaf priority {
      type uint8 {
        range "0..7";
      }
      default "0";
      description
        "802.1p priority.";
    }
    leaf precision {
      when "../measure='throughput'";
      type uint32 {
        range "1..10000";
      }
      default "1000";
      description
        "Throughput Test Precision (kbit/s)..";
    }
    leaf fail-ratio {
      type uint32 {
        range "0..10000000";
      }
      default "0";
      description
        "Loss ratio (%), determining whether the test is sucessful.";
    }
    leaf fail-ratio-unit {
      type test-ratio-unit-type;
      must '../fail-ratio or (not(../fail-ratio) and not(../fail-ratio-unit))';
      description
        "Loss ratio unit(10e-4 or 10e-9).";
    }
    leaf exchange-port-enable {
      type boolean;
      default "false";
      description
        "Enable exchange port.";
    }
    leaf rate-class {
      type test-rate-type;
      description
        "Rate class.";
    }
    leaf result-num {
      type uint32 {
        range "1..10";
      }
      default "5";
      description
        "Result record number of test instance.";
    }
    leaf description {
      type string {
        length "1..230";
      }
      description
        "Description of test instance.";
    }
    leaf age-time {
      type pub-type:time;
      default "00:00:00";
      description
        "Aging time of test instance.";
    }
  }

  grouping ethernet-service-intance-input {
    description
      "Ethernet service test intance input parameters.";
    leaf fwd-simu-if-name {
      type leafref {
        path "/ifm:ifm/ifm:interfaces/ifm:interface/ifm:name";
      }
      description
        "Forwarding-simulation inbound interface.";
    }
    leaf config-duration {
      type uint32 {
        range "1..60";
      }
      default "3";
      description
        "Configuration test duration time.";
    }
    leaf perf-duration {
      type uint32 {
        range "1..1440";
      }
      default "15";
      description
        "Performance test duration time.";
    }
    leaf profile {
      type ethsvc-profile;
      default "profile-none";
      description
        "Packet profile.";
    }
    leaf data-size-list {
      type string {
        length "1..50";
      }
      description
        "Packet size value (including the Ethernet packet head).";
    }
    container testflow-ids {
      description
        "Test instance referenced test flow list.";
      uses nqa:testflow-ids-type;
    }
  }

  grouping groups-type {
    description
      "NQA group.";
    list group {
      key "group-name";
      max-elements 16;
      description
        "NQA group.";
      leaf group-name {
        type string {
          length "1..32";
        }
        description
          "NQA group name.";
      }
      container group-members {
        ext:hidden ui;
        description
          "NQA group member.";
        list group-member {
          key "admin-name test-name";
          description
            "NQA group members.";
          leaf admin-name {
            type leafref {
              path "/nqa/instances/instance/admin-name";
            }
            description
              "Admin name.";
          }
          leaf test-name {
            type leafref {
              path "/nqa/instances/instance/test-name";
            }
            description
              "Test name.";
          }
        }
      }
    }
  }
}

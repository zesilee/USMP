/*
Copyright (C) 2019-2020 Huawei Technologies Co., Ltd. All rights reserved.
*/
submodule huawei-nqa-reflector {
  yang-version 1;
  belongs-to huawei-nqa {
    prefix nqa;
  }

  import huawei-pub-type {
    prefix pub-type;
  }
  import ietf-inet-types {
    prefix inet;
  }
  import ietf-yang-types {
    prefix yang;
  }
  import huawei-ifm {
    prefix ifm;
  }
  include huawei-nqa-testflow;

  organization
    "Huawei Technologies Co., Ltd.";
  contact
    "Huawei Industrial Base
     Bantian, Longgang
     Shenzhen 518129
     People's Republic of China
     Website: http://www.huawei.com
     Email: support@huawei.com";
  description
    "Description of submodule nqa-reflector.";
  revision 2020-02-29 {
    description
      "Modify range for pe-vlan and ce-vlan.";
    reference
      "Huawei private.";
  }
  revision 2020-01-13 {
    description
      "Modify for reflect-flow-ids.";
    reference
      "Huawei private.";
  }
  revision 2019-10-25 {
    description
      "Init revision.";
    reference
      "Huawei private.";
  }

  typedef reflect-type {
    type enumeration {
      enum interface-all {
        value 0;
        description
          "Interface all.";
      }
      enum flow-general {
        value 2;
        description
          "General flow.";
      }
      enum flow {
        value 3;
        description
          "Test flow.";
      }
    }
    description
      "description of reflect-type";
  }

  grouping reflectors-type {
    description
      "Reflector table.";
    list reflector {
      key "reflector-id";
      description
        "Reflector table.";
      leaf reflector-id {
        type uint32 {
          range "1..65535";
        }
        description
          "Reflector ID.";
      }
      leaf if-name {
        type leafref {
          path "/ifm:ifm/ifm:interfaces/ifm:interface/ifm:name";
        }
        mandatory true;
        description
          "Reflector interface name.";
      }
      leaf survival-time {
        type uint32;
        units "s";
        config false;
        description
          "Reflector survival time.";
      }
      leaf exchange-port {
        type boolean;
        default "false";
        description
          "Reflector UDP port exchange.";
      }
      leaf reflector-type {
        type reflect-type;
        mandatory true;
        description
          "Reflector type.";
      }
      container reflect-flow-ids {
        must "not(../reflector-type='flow') or (../reflector-type='flow' and count(reflect-flow-id)>=1)";
        description
          "Reflector referenced test flow list.";
        list reflect-flow-id {
          key "flow-id";
          max-elements 16;
          description
            "Reflector referenced test flow table.";
          leaf flow-id {
            type leafref {
              path "/nqa/testflows/testflow/testflow-id";
            }
            description
              "Reflector referenced test flow ID.";
          }
        }
      }
      choice address {
        description
        "Reflector Address.";
        case ipv4-address{
          description
          "Reflector IPv4 Address.";
          leaf ipv4-address {
            type inet:ipv4-address-no-zone;
            must "../reflector-type='flow-general'";
            description
            "Reflector IPv4 Address.";
          }
        }
        case simulate-ipv4-address {
          description
            "Reflector Simulate IPv4 Address.";
          leaf simulate-ipv4-address {
            type inet:ipv4-address-no-zone;
            must "../reflector-type='flow-general'";
            description
            "Reflector Simulate IPv4 Address.";
          }
        }
        case mac-address {
          description
          "Reflector MAC Address.";
          leaf mac-address {
            type pub-type:mac-address;
            must "../reflector-type='flow-general'";
            description
            "Reflector MAC Address.";
          }
        }
      }
      leaf pe-vlan {
        type uint16 {
          range "1..4094";
        }
        must "../reflector-type='flow-general' and ../pe-vlan and ../ce-vlan";
        description
          "Reflector PE VLAN ID.";
      }
      leaf ce-vlan {
        type uint16 {
          range "1..4094";
        }
        must "../reflector-type='flow-general'";
        description
          "Reflector CE VLAN ID.";
      }
      leaf source-port {
        type uint16 {
          range "0..65535";
        }
        must "../reflector-type='flow-general'";
        default "49184";
        description
          "Reflector Source Port.";
      }
      leaf dest-port {
        type uint16 {
          range "0..65535";
        }
        must "../reflector-type='flow-general'";
        default "7";
        description
          "Reflector Destination Port.";
      }
      leaf end-time {
        type yang:date-and-time;
        mandatory true;
        description
          "Absolute time of reflector aging.";
      }
      leaf share-mode {
        type boolean;
        must "../share-mode = 'false' or ../reflector-type='flow-general'";
        default "false";
        description
          "Enable the share mode on the reflector.";
      }
      leaf recommended-test-mac {
        type pub-type:mac-address;
        config false;
        description
          "Reflector Recommended MAC Address.";
      }
    }
  }
}

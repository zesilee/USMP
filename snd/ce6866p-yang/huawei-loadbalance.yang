/*
Copyright (C) 2019-2023 Huawei Technologies Co., Ltd. All rights reserved.
*/
module huawei-loadbalance {
  yang-version 1;
  namespace "urn:huawei:yang:huawei-loadbalance";
  prefix loadbalance;
  import huawei-ifm {
    prefix ifm;
  }
  import huawei-bgp {
    prefix bgp;
  }
  import huawei-pub-type {
    prefix pub-type;
  }
  import huawei-extension {
    prefix ext;
  }
  import huawei-devm {
    prefix devm;
  }
  import ietf-inet-types {
    prefix inet;
  }
  import huawei-network-instance {
    prefix ni;
  }
  organization
    "Huawei Technologies Co., Ltd.";
  contact
    "Huawei Industrial Base
    Bantian, Longgang
    Shenzhen 518129
    People's Republic of China
    Website: http://www.huawei.com
    Email: support@huawei.com";
  description
    "Load balancing.";
  revision 2023-08-31 {
    description
      "Add must.";
    reference
      "Huawei private.";
  }
  revision 2023-06-25 {
    description
      "P6 modify.";
    reference
      "Huawei private.";
  }
  revision 2023-02-27 {
    description
      "Modify infos node.";
    reference
      "Huawei private.";
  }
  revision 2023-02-16 {
    description
        "Add flow-label-bit node and modify flow-label-disable node as choice-case.";
    reference
        "Huawei private.";
  }
  revision 2023-01-17 {
    description
      "Modify must condition.";
    reference
      "Huawei private.";
  }
  revision 2022-12-19 {
    description
      "Add must condition.";
    reference
      "Huawei private.";
  }
  revision 2022-12-02 {
    description
      "Update when condition.";
    reference
      "Huawei private.";
  }
  revision 2022-11-17 {
    description
      "Add ecmp-hash-mode enum.";
    reference
      "Huawei private.";
  }
  revision 2022-11-08 {
    description
      "Add gtp-teid node.";
    reference
      "Huawei private.";
  }
  revision 2022-08-18 {
    description
      "Add load-balance-ecmp-rail-group.";
    reference
      "Huawei private.";
  }
  revision 2022-08-08 {
    description
      "Modify load-balance-ecmp-stateful-enhanced.";
    reference
      "Huawei private.";
  }
  revision 2022-07-28 {
    description
      "Modify gap-time and ip-tunnel-hash.";
    reference
      "Huawei private.";
  }
  revision 2022-06-20 {
    description
      "Modify nodes.";
    reference
      "Huawei private.";
  }
  revision 2022-06-06 {
    description
      "Add nodes.";
    reference
      "Huawei private.";
  }
  revision 2022-04-22 {
    description
      "Modify flowlet-gap-time.";
    reference
      "Huawei private.";
  }
  revision 2022-04-16 {
    description
      "Add container load-balance-ecmp-stateful-enhanced.";
    reference
      "Huawei private.";
  }
  revision 2022-04-13 {
    description
      "Modify ucmp-enable node as choice-case.";
    reference
      "Huawei private.";
  }
  revision 2022-03-18 {
    description
      "Add container dlb-enables, dynamic-ecmp-mode.";
    reference
      "Huawei private.";
  }
  revision 2022-03-09 {
    description
      "Add disable flow-label node.";
    reference
      "Huawei private.";
  }
  revision 2021-06-22 {
    description
      "Add nodes.";
    reference
      "Huawei private.";
  }
  revision 2021-05-26 {
    description
	"Add hash-arithmetic-trunk-enhance node.";
    reference	 	 	 
	"Huawei private.";	
  }
  revision 2021-04-09 {
    description
      "Update nodes.";
    reference
      "Huawei private.";
  }
  revision 2020-06-16 {
    description
      "Add leaf bfd-vxlan-bundle-random-hash, vxlan-overlay-local-preference, container ucmp-weight.";
    reference
      "Huawei private.";
  }
  revision 2020-06-15 {
    description
      "Update nodes.";
    reference
      "Huawei private.";
  }
  revision 2020-05-11 {
    description
      "Update nodes.";
    reference
      "Huawei private.";
  }
  revision 2020-05-07 {
    description
      "Update nodes.";
    reference
      "Huawei private.";
  }
  revision 2020-04-20 {
    description
      "Update nodes.";
    reference
      "Huawei private.";
  }
  revision 2020-02-18 {
    description
	"Add private grammar.";
    reference	 	 	 
	"Huawei private.";	 	 	 
  }
  revision 2020-01-22 {
    description
	"Add new nodes.";
    reference	 	 	 
	"Huawei private.";	 	 	 
  }
  revision 2020-01-13 {
    description
	"Add new nodes.";
    reference	 	 	 
	"Huawei private.";	 	 	 
  }
  revision 2019-12-18 {
    description
	"Add new nodes.";
    reference	 	 	 
	"Huawei private.";	 	 	 
  }
  revision 2019-09-04 {	 	 	 
    description	 	 	 
      "Add new nodes.";		 	 
    reference	 	 	 
      "Huawei private.";	 	 	 
  }
  revision 2019-04-01 {
    description
      "Initial revision.";
    reference
      "Huawei private.";
  }
  typedef forward-type {
    type enumeration {
      enum "ipv4" {
        value 0;
        description
          "IPv4 two-level load balancing.";
      }
      enum "ipv6" {
        value 1;
        description
          "IPv6 two-level load balancing.";
      }
      enum "mpls" {
        value 2;
        description
          "MPLS packet two-level load balancing.";
      }
      enum "vll" {
        value 3;
        description
          "VLL packet two-level load balancing.";
      }
    }
    description
      "Forward type.";
  }
  typedef hash-arithmetic {
    type enumeration {
      enum "arithmetic1" {
        value 1;
        description
          "Arithmetic 1.";
      }
      enum "arithmetic2" {
        value 2;
        description
          "Arithmetic 2.";
      }
      enum "arithmetic3" {
        value 3;
        description
          "Arithmetic 3.";
      }
    }
    description
      "Load balancing arithmetic.";
  }
  typedef hash-type {
    type enumeration {
      enum "arithmetic" {
        value 3;
        description
          "Set the hash algorithm.";
      }
      enum "box" {
        value 1;
        description
          "Hash box.";
      }
      enum "fields" {
        value 4;
        description
          "Hash fields.";
      }
      enum "seed" {
        value 2;
        description
          "Hash seed random number.";
      }
    }
    description
      "Load balancing hash type.";
  }
  typedef trunk-ecmp {
    type enumeration {
      enum "invalid" {
        value 0;
        description
          "Invalid value.";
      }
      enum "ecmp" {
        value 4;
        description
          "IIP module load balancing.";
      }
      enum "ecmp1" {
        value 1;
        description
          "IIP module one-level load balancing.";
      }
      enum "ecmp2" {
        value 2;
        description
          "IIP module two-level load balancing.";
      }
      enum "trunk" {
        value 3;
        description
          "Trunk mode.";
      }
      enum "ip" {
        value 5;
        description
          "IP mode.";
      }
      enum "mac" {
        value 6;
        description
          "MAC mode.";
      }
      enum "vll" {
        value 7;
        description
          "VLL mode.";
      }
    }
    description
      "Load balancing trunk ecmp.";
  }
  typedef hash-material {
    type enumeration {
      enum "invalid" {
        value 0;
        description
          "Invalid value.";
      }
      enum "l2" {
        value 1;
        description
          "L2 (Hash based on the source MAC address and destination MAC address. If the source IP address and destination IP address of the uplink traffic on the interface board remain unchanged but the MAC address changes, L2 is recommended as the hash factor.).";
      }
      enum "l3" {
        value 2;
        description
          "L3 (Hash based on the source IP address and destination IP address. If the source IP address and destination IP address of the uplink traffic on the interface board are evenly distributed, L3 is recommended as the hash factor.).";
      }
      enum "l4" {
        value 3;
        description
          "L4 (Hash based on the source IP address, destination IP address, source port number, destination port number, and protocol number. If the source IP address and destination IP address of the uplink traffic on the interface board are not evenly distributed, L4 is recommended as the hash factor.).";
      }
    }
    description
      "Load balancing hash material.";
  }
  typedef cx-hash-arithmetic {
    type enumeration {
      enum "arithmetic1" {
        value 1;
        description
          "Arithmetic 1.";
      }
      enum "arithmetic2" {
        value 2;
        description
          "Arithmetic 2.";
      }
      enum "arithmetic3" {
        value 3;
        description
          "Arithmetic 3.";
      }
      enum "arithmetic4" {
        value 4;
        description
          "Arithmetic 4.";
      }
      enum "arithmetic5" {
        value 5;
        description
          "Arithmetic 5.";
      }
      enum "random" {
        value 6;
        description
          "Random algorithm.";
      }
    }
    description
      "CX load balancing arithmetic.";
  }
  typedef cx-trunk-ecmp {
    type enumeration {
      enum "ip" {
        value 5;
        description
          "IP mode.";
      }
      enum "mac" {
        value 6;
        description
          "MAC mode.";
      }
      enum "vll" {
        value 7;
        description
          "VLL mode.";
      }
      enum "tunnel-info" {
        value 8;
        description
          "Tunnel information.";
      }
      enum "tunnel-inner-ip" {
        value 9;
        description
          "Tunnel inner IP information.";
      }
      enum "gtp" {
        value 10;
        description
          "GTP tunnel.";
      }	  
      enum "fec" {
        value 11;
        description
          "FEC mode.";
      }
      enum "gtp-inner-ip" {
        value 12;
        description
          "GTP tunnel inner IP information.";
      } 
    }
    description
      "CX load balancing trunk ecmp.";
  }
  typedef cx-hash-material {
    type enumeration {
      enum "l2" {
        value 1;
        description
          "L2 (Hash based on the source MAC address and destination MAC address. If the source IP address and destination IP address of the uplink traffic on the interface board remain unchanged but the MAC address changes, L2 is recommended as the hash factor.).";
      }
      enum "l3" {
        value 2;
        description
          "L3 (Hash based on the source IP address and destination IP address. If the source IP address and destination IP address of the uplink traffic on the interface board are evenly distributed, L3 is recommended as the hash factor.).";
      }
      enum "l4" {
        value 3;
        description
          "L4 (Hash based on the source IP address, destination IP address, source port number, destination port number, and protocol number. If the source IP address and destination IP address of the uplink traffic on the interface board are not evenly distributed, L4 is recommended as the hash factor.).";
      }
      enum "undo-disable" {
        value 4;
        description
          "Enable the tunnel information function for the hash factor when an IP tunnel's fragmented packets are balanced.";
      }
      enum "disable" {
        value 5;
        description
          "Disable the tunnel information function for the hash factor when an IP tunnel's fragmented packets are balanced.";
      }
      enum "label-ip" {
        value 6;
        description
          "Label-IP.";
      }
      enum "label" {
        value 7;
        description
          "Pw-label in VLL.";
      }
    }
    description
      "CX load balancing hash material.";
  }
  typedef cx-mulpe-flag {
    type enumeration {
      enum "enable" {
        value 0;
        description
          "Enable multi-path load balancing.";
      }
      enum "disable" {
        value 255;
        description
          "Disable multi-path load balancing.";
      }
    }
    description
      "CX load balancing multi-path.";
  }
  typedef hash-ip-type {
    type enumeration {
      enum "destination-ip" {
        value 4;
        description
          "Use destination IP addresses as hash key.";
      }
      enum "source-ip" {
        value 5;
        description
          "Use source IP addresses as hash key.";
      }
    }
    description
      "Hash key type.";
  }
  typedef cfg-type {
    type enumeration {
      enum "all" {
        value 0;
        description
          "Query load balancing hash information on all boards.";
      }
      enum "slot" {
        value 1;
        description
          "Query load balancing hash information on a board.";
      }
    }
    description
      "Query mode.";
  }
  typedef hash-bits {
    type enumeration {
      enum "bit-20" {
        value 0;
        description
          "Use 20bit as load balance hash-fields flow-label.";
      }
      enum "bit-16" {
        value 1;
        description
          "Use 16bit as load balance hash-fields flow-label.";
      }
    }
    description
      "Hash bit type.";
  }
  typedef port-hash-type {
    type enumeration {
      enum "source-ip" {
        value 1;
        description
          "Use source IP addresses to calculate udp source port.";
      }
    }
    description
      "Port hash type.";
  }
  typedef ecmp-hash-mode {
    type enumeration {
      enum "mode0" {
        value 0;
        description
          "Default hash algorithm.";
      }
      enum "mode1" {
        value 1;
        description
          "Polynomial A.";
      }
      enum "mode2" {
        value 2;
        description
          "Polynomial B.";
      }
      enum "mode3" {
        value 3;
        description
          "Polynomial C.";
      }
      enum "mode4" {
        value 4;
        description
          "Polynomial D.";
      }
      enum "mode5" {
        value 5;
        description
          "Polynomial E.";
      }
      enum "mode6" {
        value 6;
        description
          "Polynomial F.";
      }
      enum "mode7" {
        value 7;
        description
          "Polynomial G.";
      }
      enum "mode8" {
        value 8;
        description
          "Polynomial H.";
      }
      enum "mode9" {
        value 9;
        description
          "Polynomial I.";
      }
      enum "mode10" {
        value 10;
        description
          "Polynomial J.";
      }
      enum "mode11" {
        value 11;
        description
          "Polynomial K.";
      }
      enum "mode12" {
        value 12;
        description
          "Polynomial L.";
      }
      enum "mode13" {
        value 13;
        description
          "Polynomial M.";
      }
      enum "mode14" {
        value 14;
        description
          "Polynomial N.";
      }
      enum "mode15" {
        value 15;
        description
          "Polynomial O.";
      }
    }
    description
      "Ecmp load balancing hash mode.";
  }
  typedef local-preference-mode {
    type enumeration {
      enum "local-preference" {
        value 1;
        description
          "Local-preference mode.";
      }
      enum "network-local-preference" {
        value 2;
        description
          "Network local-preference mode.";
      }
    }
    description
      "Vxlan overlay local preference mode.";
  }
  typedef dynamic-ecmp-mode-type {
    type enumeration {
      enum "eligible" {
        value 0;
        description
          "Eligible mode.";
      }
      enum "spray" {
        value 1;
        description
          "Spray mode.";
      }
      enum "fixed" {
        value 2;
        description
          "Fixed mode.";
      }
    }
    description
      "ECMP dynamic mode.";
  }
  typedef vxlan-overlay-local-preference-mode {
    type enumeration {
      enum "vxlan" {
        value 1;
        description
          "Effective for packets from vxlan tunnel.";
      }
      enum "all" {
        value 2;
        description
          "Effective for all packets.";
      }
    }
    description
      "Vxlan overlay local preference mode.";
  }
  typedef ip-load-balance-type {
    type enumeration {
      enum "flow" {
        value 1;
        description
          "Flow mode.";
      }
      enum "packet" {
        value 2;
        description
          "Packet mode.";
      }
    }
    description
      "The load balancing mode for IP packet forwarding.";
  }

  ext:task-name "forwarding";
  container loadbalance {
    description
      "Load balancing configuration.";
    container global-attribute {
      description
        "Configure global attribute.";
      choice unequal-cost {
        ext:hidden ui;
        default "ucmp";
        description
        "Configure load balance unequal cost.";
        case ucmp {
          description
          "Configure load balance unequal cost.";
          leaf ucmp-enable {
            type boolean;
            default "false";
            description
              "Enable/disable UCMP globally.";
          }
        }
        case ucmp-bandwidth-config {
          description
          "Configure load balance unequal cost bandwidth config.";
          leaf ucmp-bandwidth-config-enable {
            type empty;
            description
              "Enable/disable UCMP bandwidth-config globally.";
          }
        }
      }
      leaf avoid-ipv4-enable {
        type boolean;
        ext:hidden ui;
        default "false";
        description
          "Enable/disable two-level load balancing for IPv4 packets.";
      }
      leaf avoid-ipv6-enable {
        type boolean;
        ext:hidden ui;
        default "false";
        description
          "Enable/disable global IPv6 hash configuration.";
      }
      leaf avoid-mpls-enable {
        type boolean;
        ext:hidden ui;
        default "false";
        description
          "Enable/disable global MPLS hash configuration.";
      }
      leaf mpls-ucmp-enable {
        type boolean;
        ext:hidden ui;
        default "false";
        description
          "Enable/disable MPLS UCMP.";
      }
      leaf mpls-sr-transit-enable {
        type boolean;
        ext:hidden ui;
        default "false";
        description
          "Enable/disable MPLS transit node segment-routing enhance.";
      }
      leaf mpls-trunk-enhance-fwd {
        type boolean;
        ext:hidden ui;
        default "false";
        description
          "Enable/disable MPLS trunk hash enhance forward.";
      }
      leaf vxlan-l2vni-enable {
        type boolean;
        ext:hidden ui;
        default "false";
        description
          "Enable/disable L2VXLAN VNI-based load balancing.";
      }
      leaf vxlan-l3vni-enable {
        type boolean;
        ext:hidden ui;
        default "false";
        description
          "Enable/disable L3VXLAN VNI-based load balancing.";
      }
      leaf vxlan-l2deep-hash-enable {
        type boolean;
        ext:hidden ui;
        default "false";
        description
          "Enable/disable L2VXLAN DEEP HASH load balancing.";
      }
      leaf trunk-enhance-fwd {
        type boolean;
        ext:hidden ui;
        default "false";
        description
          "Enable/disable trunk UCMP.";
      }
      leaf trunk-multicast-enable {
        type boolean;
        ext:hidden ui;
        default "false";
        description
          "Enable/disable trunk multicast load balancing.";
      }
      leaf mpls-te-convergence-enable {
        type boolean;
        ext:hidden ui;
        default "false";
        status obsolete;
        description
          "Enable/disable MPLS TE convergence separate.";
      }
      leaf mpls-loadblc-wtr {
        type uint32 {
          range "0|5..60";
        }
        units "s";
        ext:hidden ui;
        default "0";
        description
          "Configures the delay time for MPLS equal-cost multiple path (ECMP) switchback.";
      }
      leaf dynamic-enable {
        type boolean;
        default "false";
        description
          "Enable/disable dynamic load balance.";
      }
      leaf tunnel-info-gtp-enable {
        type boolean;
        ext:hidden ui;
        default "true";
        description
          "Enable/disable GTP deep hash load balancing.";
      }    
      container hash-arithmetic-trunk-enhance {
        ext:hidden ui;
        presence "Enable hash arithmetic trunk enhance";
        description
          "Enable/disable load balance hash-arithmetic trunk-enhance.";
      }
      choice flow-label {
        ext:hidden ui;
        default "hash-bit";
        description
          "Configure load balance flow label.";
        case disable {
          description
            "Configure load balance flow label disable.";
          container flow-label-disable {
            presence "Disable load balance hash-fields flow-label";
            description
              "Enable/disable load balance hash-fields flow-label.";
          }
        }
        case hash-bit {
          description
            "Configure load balance flow label bits.";
          leaf flow-label-bit {
            type hash-bits;
            default "bit-20";
            description
              "Configure flow label use 16bit or 20bit globally.";
          }
        }
      }
      leaf rail-group-enable {
        type boolean;
		must "not(../rail-group-enable = 'true' and (../../load-balance-ecmp-enable/is-enable = 'true' or ../../load-balance-ecmp-profile/vxlan-overlay-local-preference/local-preference-mode or /ni:network-instance/ni:instances/ni:instance[ni:name='/ni:network-instance/ni:instances/ni:instance/ni:name']/bgp:bgp/bgp:base-process/bgp:afs/bgp:af[bgp:type = 'ipv4uni']/bgp:ipv4-unicast/bgp:load-balancing/bgp:adaptive-routing or /ni:network-instance/ni:instances/ni:instance[ni:name='_public_']/bgp:bgp/bgp:base-process/bgp:afs/bgp:af[bgp:type = 'ipv4uni']/bgp:ipv4-unicast/bgp:common/bgp:load-balancing-ucmp = 'true' or /ni:network-instance/ni:instances/ni:instance[ni:name='_public_']/bgp:bgp/bgp:base-process/bgp:afs/bgp:af[bgp:type = 'ipv6uni']/bgp:ipv6-unicast/bgp:common/bgp:load-balancing-ucmp = 'true'))";
        default "false";
        description
        "Enable/disable load-balance ECMP rail-group enable.";
      }
    }
    container load-balance-ecmp-profile {
        description
          "Configure load-balance ecmp.";
        container ecmp-attribute {
          description
            "Configure ECMP attribute.";
          leaf gtp-teid {
            type empty;
            description
              "Enable/disable the TEID-based hash function for GTP packets.";
          }
        }
        container ip-hash {
          must "not(sip='false' and dip='false' and vlan='false' and l4sport='false' and l4dport='false' and protocol='false' and src-interface='false' and flowlabel='false')";
		  description "Configure ECMP hash elements of IP packet.";                
          leaf sip {
            type boolean;
            default "true";
            description "Enable/disable source IP.";
          }
          leaf dip {
            type boolean;
            default "true";
            description "Enable/disable destination IP.";
          }
          leaf vlan {
            type boolean;
            default "false";
            description "Enable/disable VLAN.";
          }
          leaf l4sport {
            type boolean;
            default "true";
            description "Enable/disable source port.";
          }
          leaf l4dport {
            type boolean;
            default "true";
            description "Enable/disable destination port.";
          }
          leaf protocol {
            type boolean;
            default "false";
            description "Enable/disable protocol number.";
          }
          leaf src-interface {
            type boolean;
            default "false";
            description "Enable/disable source interface.";
          }
          leaf flowlabel {
            type boolean;
            default "false";
            description "Enable/disable flow-label.";
          }
          leaf dscp {
            type boolean;
            default "false";
            description "Enable/disable DSCP.";
          }
        }
        container ip-tunnel-hash {
          description "Configure ECMP hash elements of IPinIP packet."; 
          leaf inner-src-ip {
            type boolean;
            default "true";
            description "Enable/disable inner source IP address.";
          }
          leaf inner-dst-ip {
            type boolean;
            default "true";
            description "Enable/disable inner destination IP address.";
          }
          leaf inner-l4-dport {
            type boolean;
            default "true";
            description "Enable/disable inner destination L4 port.";
          }
          leaf inner-l4-sport {
            type boolean;
            default "true";
            description "Enable/disable inner source L4 port.";
          }
          leaf inner-protocol {
            type boolean;
            default "false";
            description "Enable/disable inner protocol.";
          }
          leaf src-interface {
            type boolean;
            default "false";
            description "Enable/disable source interface.";
          }
          leaf src-mac {
            type boolean;
            default "false";
            description "Enable/disable source Mac.";
          }
          leaf dst-mac {
            type boolean;
            default "false";
            description "Enable/disable dest Mac.";
          }
          leaf include-erspan {
            type boolean;
            default "false";
            description "Enable/disable ERSPAN inner packets.";
          }
        }
		container vxlan-hash {
          must "not(inner-src-ip='false' and inner-dst-ip='false' and inner-l4-dport='false' and inner-l4-sport='false' and inner-protocol='false' and src-interface='false' and vni='false')";
          description "Configure ECMP hash elements of vxlan packet.";
          leaf inner-src-ip {
            type boolean;
            default "true";
            description "Enable/disable inner source IP address.";
          }
          leaf inner-dst-ip {
            type boolean;
            default "true";
            description "Enable/disable inner destination IP address.";
          }
          leaf inner-l4-dport {
            type boolean;
            default "true";
            description "Enable/disable inner destination L4 port.";
          }
          leaf inner-l4-sport {
            type boolean;
            default "true";
            description "Enable/disable inner source L4 port.";
          }
          leaf inner-protocol {
            type boolean;
            default "true";
            description "Enable/disable inner protocol.";
          }
          leaf src-interface {
            type boolean;
            default "false";
            description "Enable/disable source interface.";
          }
          leaf vni {
            type boolean;
            default "false";
            description "Enable/disable VNI.";
          }
        }
      container load-balance-ecmp-hashmode {
        description "Configure load-balance ECMP hash mode.";
        leaf hash-mode {
          type ecmp-hash-mode;
          default "mode0";
          description "Hash mode.";
        }
        leaf bfd-vxlan-bundle-random-hash {
          type boolean;
          ext:hidden ui;
          default "false";
          description
            "Enable/disable bfd vxlan-bundle random-hash.";
        }
        leaf vxlan-overlay-local-preference {
          type local-preference-mode;
          ext:hidden ui;
          description
            "Specify vxlan-overlay local-preference mode.";
        }
        leaf overlay-hash-mode {
          type ecmp-hash-mode;
          default "mode0";
          description "Overlay hash mode.";
        }
        leaf underlay-hash-mode {
          type ecmp-hash-mode;
          default "mode0";
          description "Underlay hash mode.";
        }
      }
      container load-balance-ecmp-universal {
        description "Configure load-balance ECMP universal ID.";
        leaf universal-id {
          type uint32 {
            range "1..16";
          }
          default "1";
          description "Universal ID.";
        }
        leaf underlay-universal-id {
          type uint32 {
            range "0..15";
          }
          must "not(../../../global-attribute/rail-group-enable = 'true' and ../underlay-universal-id != 0)";
          default "0";
          description "Underlay universal ID.";
        }
        leaf overlay-universal-id {
          type uint32 {
            range "0..15";
          }
          default "1";
          description "Overlay universal ID.";
        }
      }
      container load-balance-ecmp-seed {
        description "Configure load-balance ECMP seed data.";
        leaf seed-data {
          type uint32 {
            range "0..255";
          }
          default "1";
          description "Seed data.";
        }
        leaf underlay-seed-data {
          type uint32 {
            range "0..255";
          }
          must "not(../../../global-attribute/rail-group-enable = 'true' and ../underlay-seed-data != 0)";
          default "0";
          description "Underlay seed data.";
        }
        leaf overlay-seed-data {
          type uint32 {
            range "0..255";
          }
          default "1";
          description "Overlay seed data.";
        }
      }
      container ecmp-local-preference
      {
        description
          "Configure ECMP local-chassis preferential forwarding.";	  
        leaf enable {
          type boolean;
          default "true";
          description
            "Enable/disable preferential forwarding of ECMP packets on the local chassis.";
        }
      }
      container dynamic-ecmp-mode {
        description
          "Configure equal cost multipath routing dymamic ECMP mode.";
        leaf mode {
          type dynamic-ecmp-mode-type;
          default "eligible";
          description "ECMP dynamic mode.";
        }
        leaf flowlet-gap-time {
          when "../mode='eligible'";
          type uint32 {
            range "16..32000";
          }
          default "2000";
          description "Flowlet gap time. Unit 1024ns. Recommended configuration : 16 ~ 32000.";
        }
      }
      container local-preference-enhanced
      {
        description
          "Configure ECMP local-chip preferential forwarding.";	  
        leaf enable {
          type boolean;
          default "false";
          description
            "Enable/disable preferential forwarding of ECMP packets on the local chip.";
        }
      }
      container vxlan-overlay-local-preference
      {
        description
          "Configure vxlan overlay local preference.";	  
        leaf local-preference-mode {
          type vxlan-overlay-local-preference-mode;
          description
            "Vxlan overlay local preference mode.";
        }
      }
      container ecmp-symmetry
      {
        description
            "Configure forwarding of ECMP packets with the same source and destination addresses.";	  
        leaf enable {
            type boolean;
            default "true";
            description
                "Enable/disable forwarding of ECMP packets with the same source and destination addresses.";
        }
      }
    }
    container dynamic-load-balance-profile {
      ext:hidden ui;
        description
          "Configure dynamic-load-balance.";
	    leaf time-gap {
		type uint32{
		range "0..1000";		  
		}
                units "ms";
	        default "1";
	        description
	          "Set time gap.";           
	    }
    }
    container avoid-degradations {
      ext:hidden ui;
      description
        "List of configurations of the two-level load balancing function on a board.";
      list avoid-degradation {
        key "position forward-type";
        description
          "Configure the two-level load balancing function on a board.";
        leaf position {
          type string {
            length "1..16";
          }
          description
            "Slot ID of an interface board. The value range varies according to router hardware.";
        }
        leaf forward-type {
          type forward-type;
          description
            "Set packet type.";
        }
      }
    }
    container hash-key-ip {
      ext:hidden ui;
      description
        "Configure a device to use source or destination IP addresses as hash key to balance all incoming IP packets on a specific or all interface boards.";
      leaf ip-type {
        type hash-ip-type;
        description
          "Set IP hash type.";
      }
    }
    container hash-key-ip-slots {
      ext:hidden ui;
      description
        "List of configurations that enable a device to use source or destination IP addresses as hash key to balance all incoming IP packets on a specific or all interface boards.";
      list hash-key-ip-slot {
        key "slot-id";
        description
          "Configure a device to use source or destination IP addresses as hash key to balance all incoming IP packets on a specific or all interface boards.";
        leaf slot-id {
          type string {
            length "1..32";
          }
          description
            "Slot ID of an interface board. The value range varies according to router hardware. NULL is for all slot.";
        }
        leaf ip-type {
          type hash-ip-type;
          mandatory true;
          description
            "Set IP hash type.";
        }
      }
    }
    container hash-instructions {
      ext:hidden ui;
      config false;
      description
        "List of load balancing hash information on a specified board or on all boards.";
      list hash-instruction {
        key "slot-id query-type";
        config false;
        description
          "Statistics of load balancing hash information on a specified board or on all boards.";
        leaf slot-id {
          type string {
            length "0..32";
          }
          config false;
          description
            "Slot ID of an interface board. The value range varies according to router hardware.";
        }
        leaf query-type {
          type cfg-type;
          config false;
          description
            "Query mode of load balancing hash information.";
        }
        container infos {
          config false;
          status obsolete;
          description
            "Statistics of load balancing hash-related configurations.";
          leaf info {
            type string {
              length "1..127";
            }
            config false;
            status obsolete;
            description
              "Load balancing hash information. To check load balancing information, querying the load-balancing configuration node is recommended.";
          }
        }
        leaf tunnel-gtp-enable {
            type boolean;
            config false;
            description
              "This node displays whether tunnel information is used as a hash factor during hash calculation for GTP tunnel load balancing.";
          }
      }
    }
    container ecmp-stateful {
      ext:hidden ui;
      must "maximum>minimum";
      presence "Configure ECMP stateful load balancing.";
      description
        "Configure ECMP stateful load balancing.";
      leaf minimum {
        type uint32 {
          range "1..63";
        }
        default "1";
        description
          "Minimum interface number.";
      }
      leaf maximum {
        type uint32 {
          range "2..64";
        }
        default "64";
        description
          "Maximum interface number.";
      }
      leaf accuracy {
        type uint32 {
          range "1..4";
        }
        default "1";
        description
          "Accuracy of ECMP load balancing.";
      }
    }
    container load-balance-ecmp-enable {
      description
        "Configure load-balance ECMP enable state.";
      leaf is-enable {
		type boolean;
		default "false";
        description
          "Enable/disable load-balance ECMP stateful.";
      }
    }
    container dlb-enables {
      ext:hidden ui;
      description
        "List of load-balance dynamic ECMP enable state.";
      list dlb-enable {
        key "vpn-name";
        description
          "Configure load-balance dynamic ECMP enable state.";
        leaf vpn-name {
          type leafref {
            path "/ni:network-instance/ni:instances/ni:instance/ni:name";
          }
          description
            "Specifies a VPN instance name. Public network vpn-name value is '_public_'.";
        }
      }
    }
    container load-balance-ecmp-stateful-enhanced {
      must "../load-balance-ecmp-enable/is-enable='true' or (../load-balance-ecmp-enable/is-enable='false' and is-enable='false')";
      description
        "Configure load-balance ECMP enable stateful enhanced.";
      leaf is-enable {
        type boolean;
        default "false";
        description
          "Enable/disable load-balance ECMP stateful enhanced.";
      }
    }
    container ip-load-balance {
      must "not(mode = 'flow' and src-ip = 'false' and dst-ip = 'false' and src-port = 'false' and dst-port = 'false')";
      description "Configure the load balancing mode for IP packet forwarding In the scenario of multiple outbound interfaces.";
      leaf mode {
        type ip-load-balance-type;
        default "flow";
        description "The load balancing mode for IP packet forwarding.";
      }
      leaf src-ip {
        when "(../mode = 'flow')";
        type boolean;
        default "true";
        description "Enable/disable source IP.";
      }
      leaf dst-ip {
        when "(../mode = 'flow')";    	
        type boolean;
        default "true";
        description "Enable/disable destination IP.";
      }
      leaf src-port {
        when "(../mode = 'flow')";
        type boolean;
        default "false";
        description "Enable/disable source port.";
      }
      leaf dst-port {
        when "(../mode = 'flow')";
        type boolean;
        default "false";
        description "Enable/disable destination port.";
      }
    }
    container ipv6-load-balance {
      must "not(mode = 'flow' and src-ip = 'false' and dst-ip = 'false' and src-port = 'false' and dst-port = 'false')" ;
      description "Configure the load balancing mode for IPv6 packet forwarding In the scenario of multiple outbound interfaces.";
      leaf mode {
        type ip-load-balance-type;
        default "flow";
        description "The load balancing mode for IPv6 packet forwarding.";
      }
      leaf src-ip {
        when "(../mode = 'flow')";
        type boolean;
        default "true";
        description "Enable/disable source IP.";
      }
      leaf dst-ip {
        when "(../mode = 'flow')";
        type boolean;
        default "true";
        description "Enable/disable destination IP.";
      }
      leaf src-port {
        when "(../mode = 'flow')";
        type boolean;
        default "false";
        description "Enable/disable source port.";
      }
      leaf dst-port {
        when "(../mode = 'flow')";
        type boolean;
        default "false";
        description "Enable/disable destination port.";
      }
    }
    container ip-load-balance-reverse-route-enable
    {
      description
        "Configure the load balancing function for IP reverse routes.";	  
      leaf enable {
        type boolean;
        default "false";
        description
          "Enable/disable the load balancing function for IP reverse routes.";
      }
    }
    container ipv6-load-balance-reverse-route-enable
    {
      description
        "Configure the load balancing function for IPv6 reverse routes.";	  
      leaf enable {
        type boolean;
        default "false";
        description
          "Enable/disable the load balancing function for IPv6 reverse routes.";
      }
    }
  }
  augment "/ifm:ifm/ifm:interfaces/ifm:interface" {
    description
      "Load balancing configuration to the ifm module.";
    container loadbalance {
      ext:hidden ui;
      description
        "Configure Load balancing.";
      container ucmp {
        when "../../ifm:type = 'GigabitEthernet' or ../../ifm:type = 'Pos' or ../../ifm:type = '40GE' or ../../ifm:type = '100GE' or ../../ifm:type = '1200GE' or ../../ifm:type = 'XGigabitEthernet' or ../../ifm:type = 'ATM' or ../../ifm:type = '50|100GE' or ../../ifm:type = '50GE' or ../../ifm:type = '400GE' or ../../ifm:type = '25GE' or ../../ifm:type = '200GE' or ../../ifm:type = '10GE' or ../../ifm:type = 'FlexE' or ../../ifm:type = '4x10GE' or ../../ifm:type = '10x10GE' or ../../ifm:type = '3x40GE' or ../../ifm:type = '4x25GE' or ../../ifm:type = 'Ethernet'";
        presence "Enable UCMP on the interface";
        description
          "Enable/disable UCMP on an interface. To implement UCMP on equal-cost links with different bandwidth values, you can configure this function on each interface. Enabling or disabling UCMP on a physical interface takes effect only after the interface is restarted. UCMP is only for equal-cost routes. UCMP applies only to equal-cost routes and is independent of routing protocols, such as an IGP or BGP.";
      }
	  container ucmp-weight {
        when "../../ifm:type = 'GigabitEthernet' or ../../ifm:type = 'Pos' or ../../ifm:type = '40GE' or ../../ifm:type = '100GE' or ../../ifm:type = 'XGigabitEthernet' or ../../ifm:type = 'ATM' or ../../ifm:type = '50|100GE' or ../../ifm:type = '50GE' or ../../ifm:type = '400GE' or ../../ifm:type = '25GE' or ../../ifm:type = '200GE' or ../../ifm:type = '10GE' or ../../ifm:type = 'FlexE' or ../../ifm:type = '4x10GE' or ../../ifm:type = '10x10GE' or ../../ifm:type = '3x40GE' or ../../ifm:type = '4x25GE' or ../../ifm:type = 'Ethernet' or ../../ifm:type = 'Vlanif' or ../../ifm:type = 'Eth-Trunk' or ../../ifm:type = 'Vbdif'";
        description
          "Configure ucmp weight.";
        container nexthops {
          description
            "List of nexthops for interfaces.";
          list nexthop {
            key "address";
            description
              "Configure nexthop of UCMP interfaces.";
            leaf address {
              type inet:ip-address-no-zone;
              description
                "Specify the nexthop ip address.";
            }
            leaf weight {
              type uint32 {
                range "0..100";
              }
              mandatory true;
              description
                "Specify the nexthop weight.";
            }
          }
        }
        leaf weight {
          type uint32 {
            range "0..100";
          }
          description
            "Specify weight of interface.";
        }
      }
      container packet {
        when "../../ifm:type = 'Ethernet' or ../../ifm:type = '100GE' or ../../ifm:type = '1200GE' or ../../ifm:type = '400GE' or ../../ifm:type = '40GE' or ../../ifm:type = 'GigabitEthernet' or ../../ifm:type = 'XGigabitEthernet' or ../../ifm:type = 'Ip-Trunk' or ../../ifm:type = 'Eth-Trunk' or ../../ifm:type = '50|100GE' or ../../ifm:type = '50GE' or ../../ifm:type = '25GE' or ../../ifm:type = '200GE' or ../../ifm:type = '10GE' or ../../ifm:type = 'FlexE' or ../../ifm:type = '4x10GE' or ../../ifm:type = '10x10GE' or ../../ifm:type = '3x40GE' or ../../ifm:type = '4x25GE'";
        presence "Enable per-packet load balancing on an interface";
        description
          "Enable/disable per-packet load balancing on specified interfaces.";
      }
      container vxlan-forward {
        when "../../ifm:type = 'VX-Tunnel' and ../../ifm:class = 'sub-interface'";
        description
          "Configure vxlan-forward on an interface.";
        leaf udp-source-port-hash-type {
          type port-hash-type;
          description
            "Hash calculation method.";
        }
      }
    } 
  }
  augment "/devm:devm/devm:lpu-boards/devm:lpu-board" {
    description
      "Load balancing configuration to the devm module.";
    container loadbalance {
      ext:hidden ui;
      description
        "Configure load balancing.";
      container hashs {
        description
          "List of PE2 hash configuration on a specified board.";
        list hash {
          key "type trunk-ecmp";
          description
            "Configure PE2 hash load balancing.";
          leaf type {
            type hash-type;
            description
              "Set hash configuration type.";
          }
          leaf trunk-ecmp {
            type trunk-ecmp;
            must "(../type='arithmetic' and ../trunk-ecmp='invalid') or (../type='box' and (../trunk-ecmp='ecmp1' or ../trunk-ecmp='ecmp2' or ../trunk-ecmp='trunk') ) or (../type='fields' and (../trunk-ecmp='ip' or ../trunk-ecmp='mac' or ../trunk-ecmp='vll') ) or (../type='seed' and (../trunk-ecmp='ecmp' or ../trunk-ecmp='trunk') ) or not(../type='arithmetic' or ../type='box' or ../type='fields' or ../type='seed')";
            description
              "Set hash mode, that is, the box attribute, indicating which load balancing mode is applicable to the box.";
          }
          leaf arithmetic {
            when "../type='arithmetic'";
            type hash-arithmetic;
            default "arithmetic2";
            description
              "Set hash algorithm.";
          }
          leaf box1 {
            when "../type='box'";
            type pub-type:hex-binary {
              length "1..4";
              pattern '(0x|0X)?[0-9a-fA-F]{1,2}';
            }
            default "0x0";
            description
              "Hash box 1.";
          }
          leaf box2 {
            when "../type='box'";
            type pub-type:hex-binary {
              length "1..10";
              pattern '(0x|0X)?[0-9a-fA-F]{1,8}';
            }
            default "0x0";
            description
              "Hash box 2.";
          }
          leaf material {
            when "../type='fields'";
            type hash-material;
            must "(../material='l2' or ../material='l3' or ../material='l4') or not(../type='fields' or ../trunk-ecmp='ip' or ../trunk-ecmp='mac')";
            default "l4";
            description
              "Set hash material.";
          }
          leaf random-flag {
            when "../type='seed'";
            type boolean;
            default "false";
            description
              "Enable/disable random flag.";
          }
          leaf custom-seed {
            when "../type='seed' and ../random-flag='false'";
            type pub-type:hex-binary {
              length "1..10";
              pattern '(0x|0X)?[0-9a-fA-F]{1,8}';
            }
            default "0x0";
            description
              "User-defined hash seed random number.";
          }
        }
      }
      container dynamic-adjust {
        description
          "Configure dynamic load balancing.";
        leaf enable {
          type boolean;
          default "false";
          description
            "Enable/disable dynamic load balancing.";
        }
      }
      container hash-arithmetic {
        description
          "Configure FE1 hash arithmetic on a specified board.";
        leaf arithmetic {
          type cx-hash-arithmetic;
          default "random";
          description
            "Set hash algorithm.";
        }
        leaf second-hash-flag {
          type boolean;
          default "false";
          description
            "Enable/disable second hash flag.";
        }
      }
      container hash-fields {
        description
          "List of FE1 hash fields configuration on a specified board.";
        list hash-field {
          key "trunk-ecmp";
          description
            "Configure hash mode, that is, the box attribute, indicating which load balancing mode is applicable to the box.";
          ext:generated-by system {
            description "The all instances are generated automatically.";
          }
          ext:operation-exclude create {
            description "The all instances cannot be created.";
          }
          leaf trunk-ecmp {
            type cx-trunk-ecmp;
            description
              "Hash mode.";
          }
          leaf material {
            type cx-hash-material;
            ext:dynamic-default {
              ext:default-value "l4" {
                when "../trunk-ecmp='ip' or ../trunk-ecmp='mac' or ../trunk-ecmp='vll'";
                description "The default value is l4 when trunk-ecmp is IP or MAC or VLL.";
              }
              ext:default-value "disable" {
                when "../trunk-ecmp='tunnel-inner-ip' or ../trunk-ecmp='gtp-inner-ip'";
                description "The default value is disable when trunk-ecmp is tunnel-inner-ip or gtp-inner-ip.";
              }
              ext:default-value "undo-disable" {
                when "../trunk-ecmp='tunnel-info' or ../trunk-ecmp='gtp'";
                description "The default value is enable when trunk-ecmp is tunnel-info or GTP.";
              }
            }
            must "(../trunk-ecmp='ip' and (../material='l2' or ../material='l3' or ../material='l4') ) or (../trunk-ecmp='mac' and (../material='l2' or ../material='l3' or ../material='l4' or ../material='label-ip') ) or ( (../trunk-ecmp='tunnel-info'  or ../trunk-ecmp='tunnel-inner-ip' or ../trunk-ecmp='gtp' or ../trunk-ecmp='gtp-inner-ip') and (../material='undo-disable' or ../material='disable') ) or (../trunk-ecmp='vll' and (../material='l2' or ../material='l3' or ../material='l4' or ../material='label-ip' or ../material='label') )";

            description
              "Set hash material.";
            ext:support-filter "true";
          }
        }
      }
      container hash-seed {
        presence "FE1 hash seed configuration on a specified board.";
        description
          "Enable/disable FE1 hash seed on a specified board.";
        leaf random-flag {
          type boolean;
          default "false";
          description
            "Enable/disable random flag.";
        }
        leaf custom-seed {
          type pub-type:hex-binary;
          must "../custom-seed='0x0' or ../random-flag='false'";
          default "0x0";
          description
            "User-defined hash seed random number.";
        }
      }
      container hash-multipe {
        description
          "Configure FE1 hash Multi-path on a specified board.";
        leaf multipe-flag {
          type cx-mulpe-flag;
          default "disable";
          description
            "Enable multi-path load balancing.";
        }
      }
    }
  }
  augment "/devm:devm/devm:mpu-boards/devm:mpu-board" {
    description
      "Load balancing configuration to the devm module.";
    container loadbalance {
      ext:hidden ui;
      description
        "Configure load balancing.";
      container dynamic-adjust {
        description
          "Configure dynamic load balancing.";
        leaf enable {
          type boolean;
          default "false";
          description
            "Enable/disable dynamic load balancing.";
        }
      }
      container hash-arithmetic {
        description
          "Configure FE1 hash arithmetic on a specified board.";
        leaf arithmetic {
          type cx-hash-arithmetic;
          default "random";
          description
            "Arithmetic.";
        }
        leaf second-hash-flag {
          type boolean;
          default "false";
          description
            "Enable/disable second hash.";
        }
      }
      container hash-fields {
        description
          "List of FE1 hash fields configuration on a specified board.";
        list hash-field {
          key "trunk-ecmp";
          description
            "Configure hash mode, that is, the box attribute, indicating which load balancing mode is applicable to the box.";
          ext:generated-by system {
            description "The all instances are generated automatically.";
          }
          ext:operation-exclude create {
            description "The all instances cannot be created.";
          }
          leaf trunk-ecmp {
            type cx-trunk-ecmp;
            description
              "Hash mode.";
          }
          leaf material {
            type cx-hash-material;
            ext:dynamic-default {
              ext:default-value "l4" {
                when "../trunk-ecmp='ip' or ../trunk-ecmp='mac' or ../trunk-ecmp='vll'";
                description "The default value is l4 when trunk-ecmp is IP or MAC or VLL.";
              }
              ext:default-value "disable" {
                when "../trunk-ecmp='tunnel-inner-ip' or ../trunk-ecmp='gtp-inner-ip'";
                description "The default value is disable when trunk-ecmp is tunnel-inner-ip or gtp-inner-ip.";
              }
              ext:default-value "undo-disable" {
                when "../trunk-ecmp='tunnel-info' or ../trunk-ecmp='gtp'";
                description "The default value is enable when trunk-ecmp is tunnel-info or GTP.";
              }
            }
            must "(../trunk-ecmp='ip' and (../material='l2' or ../material='l3' or ../material='l4') ) or (../trunk-ecmp='mac' and (../material='l2' or ../material='l3' or ../material='l4' or ../material='label-ip') ) or ( (../trunk-ecmp='tunnel-info'  or ../trunk-ecmp='tunnel-inner-ip' or ../trunk-ecmp='gtp' or ../trunk-ecmp='gtp-inner-ip') and (../material='undo-disable' or ../material='disable') ) or (../trunk-ecmp='vll' and (../material='l2' or ../material='l3' or ../material='l4' or ../material='label-ip' or ../material='label') )";

            description
              "Set hash material.";
            ext:support-filter "true";
          }
        }
      }
      container hash-seed {
        presence "FE1 hash seed configuration on a specified board.";
        description
          "Enable/disable FE1 hash seed on a specified board.";
        leaf random-flag {
          type boolean;
          default "false";
          description
            "Enable/disable random flag.";
        }
        leaf custom-seed {
          type pub-type:hex-binary;
          must "../custom-seed='0x0' or ../random-flag='false'";
          default "0x0";
          description
            "User-defined hash seed random number.";
        }
      }
      container hash-multipe {
        description
          "Configure FE1 hash Multi-PE on a specified board.";
        leaf multipe-flag {
          type cx-mulpe-flag;
          default "disable";
          description
            "Multi-path load balancing.";
        }
      }
    }
  }
}

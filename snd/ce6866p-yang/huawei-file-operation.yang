/*
Copyright (C) 2019-2022 Huawei Technologies Co., Ltd. All rights reserved.
*/
module huawei-file-operation {
  namespace "urn:huawei:yang:huawei-file-operation";
  prefix file-operation;

  import huawei-extension {
    prefix ext;
  } 

  organization
    "Huawei Technologies Co., Ltd.";
  contact
    "Huawei Industrial Base
     Bantian, Longgang
     Shenzhen 518129
     People's Republic of China
     Website: http://www.huawei.com
     Email: support@huawei.com";
  description
    "Indicate file system management.";
  revision 2022-08-18 {
    description
      "Modify node description of zip-file and zip-file's leaf node src-file-name.";
    reference
      "Huawei private.";
  }
  revision 2021-09-17 {
    description
      "Modify leafref path of the leaf file-name of rpc.";
    reference
      "Huawei private.";
  }
  revision 2021-06-17 {
    description
      "Modify leafref path of the leaf node dir-name.";
    reference
      "Huawei private.";
  }
  revision 2020-08-12 {
    description
      "Modify data type of the node size from int32 to uint32.";
    reference
      "Huawei private.";
  }
  revision 2020-04-02 {
    description
      "YANG check.";
    reference
      "Huawei private.";
  }
  revision 2020-02-13 {
    description
      "Add leaf node of copy-file and delete-file.";
    reference
      "Huawei private.";
  }
  revision 2019-12-20 {
    description
      "Modify node description.";
    reference
      "Huawei private.";
  }
  revision 2019-12-09 {
    description
      "Initial revision.";
    reference
      "Huawei private.";
  }

  ext:task-name "rpm";
  typedef delete-type {
    type enumeration {
      enum "unreserved" {
        value 0;
        description
          "Delete file permanently. The deleted file cannot be restored.";
      }
    }
    description
      "Specify the action of deleting file.";
  }

  rpc delete-file {
    description
      "Delete file permanently. A folder, however, cannot be deleted.";
    ext:node-ref "/file-operation/dirs/dir";
    input {
      leaf file-name {
        type string {
          length "1..255";
        }
        mandatory true;
        description
          "Specify a file name that can be listed in a full directory or a relative directory.";
      }
      leaf delete-type {
        type delete-type;
        mandatory true;
        description
          "Specify the action of deleting file.";
      }
      leaf all {
        type boolean;
        description
          "Delete a file of the main board and slave board permanently. A folder, however, cannot be deleted.";
      }
    }
  }

  rpc make-dir {
    description
      "Create a folder.";
    ext:node-ref "/file-operation/dirs/dir";
    input {
      leaf dir-name {
        type string {
            length "1..255";
          }
        mandatory true;
        description
          "Specify a folder that will be created.";
      }
    }
  }

}

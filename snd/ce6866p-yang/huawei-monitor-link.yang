/*
Copyright (C) 2020 Huawei Technologies Co., Ltd. All rights reserved.
*/
module huawei-monitor-link {
  namespace "urn:huawei:yang:huawei-monitor-link";
  prefix mtlk;
  import huawei-ifm {
    prefix ifm;
  }
  import huawei-extension {
    prefix ext;
  }
  import ietf-yang-types {
    prefix yang;
  }
  organization
    "Huawei Technologies Co., Ltd.";
  contact
    "Huawei Industrial Base
     Bantian, Longgang
     Shenzhen 518129
     People's Republic of China
     Website: http://www.huawei.com
     Email: support@huawei.com";
  description
    "An interface association mechanism using to expand the scope of link.";
  revision 2020-11-06 {
    description
      "Initial revision.";
    reference
      "Huawei private.";
  }
  typedef port-state {
    type enumeration {
      enum "down" {
        value 0;
        description
          "The status of interface is down.";
      }
      enum "up" {
        value 1;
        description
          "The status of interface is up.";
      }
      enum "none" {
        value 255;
        description
          "None.";
      }
    }
    description
      "The status of interface adding to monitor group link.";
  }
  ext:task-name "rgm";  
  container monitor-link {
    description
      "An interface association mechanism using to expand the scope of link.";
    container monitor-link-groups {
      description
        "List of monitor link groups.";
      list monitor-link-group {
        key "id";
        description
          "Configure monitor link group.";
        leaf id {
          type uint8 {
            range "1..24";
          }
          description
            "Monitor link group ID.";
        }
        leaf enable {
          type boolean;
          default "true";
          description
            "Enable/disable monitor link group.";
        }
        leaf recover-time {
          type uint16 {
            range "0..300";
          }
          units s;
          default "3";
          description
            "Specifies the switchback time of a monitor link group.";
        }
        container uplink-interfaces {
          description
            "List of monitor link group uplink interfaces.";
          list uplink-interface {
            key "if-name";
            description
              "Configure monitor link group uplink interface.";
            leaf if-name {
              type leafref {
                path "/ifm:ifm/ifm:interfaces/ifm:interface/ifm:name";
              }
              must "/ifm:ifm/ifm:interfaces/ifm:interface[ifm:name=current()]/ifm:class='main-interface'";
              description
                "Specifies an interface to be added to a monitor link group.";
            }
            leaf port-state {
              type port-state;
              config false;
              description
                "The state of monitor link group interface.";
            }
            leaf last-up-time {
              type yang:date-and-time;
              config false;
              description
                "The last up time of monitor link group interface.";
            }
            leaf last-down-time {
              type yang:date-and-time;
              config false;
              description
                "The last down time of monitor link group interface.";
            }
          }
        }
        container downlink-interfaces {
          description
            "List of monitor link group downlink interfaces.";
          list downlink-interface {
            key "if-name";
            unique "id";
            description
              "Configure monitor link group downlink interface.";
            leaf if-name {
              type leafref {
                path "/ifm:ifm/ifm:interfaces/ifm:interface/ifm:name";
              }
              must "/ifm:ifm/ifm:interfaces/ifm:interface[ifm:name=current()]/ifm:class='main-interface'";
              must "not(/mtlk:monitor-link/mtlk:monitor-link-groups/mtlk:monitor-link-group/mtlk:uplink-interfaces/mtlk:uplink-interface[if-name = current()])";
              description
                "Specifies an interface to be added to a monitor link group.";
            }
            leaf id {
              type uint16 {
                range "1..512";
              }
              mandatory true;
              description
                "Specifies a ID of interface to determine the sequence in which the interface goes down or up.";
            }
            leaf port-state {
              type port-state;
              config false;
              description
                "The state of monitor link group interface.";
            }
            leaf last-up-time {
              type yang:date-and-time;
              config false;
              description
                "The last up time of monitor link group interface.";
            }
            leaf last-down-time {
              type yang:date-and-time;
              config false;
              description
                "The last down time of monitor link group interface.";
            }
          }
        }
      }
    }
  }
}

/*
Copyright (C) 2020 Huawei Technologies Co., Ltd. All rights reserved.
*/
module huawei-arp-fwd {
  namespace "urn:huawei:yang:huawei-arp-fwd";
  prefix arp-fwd;
  
  import huawei-ifm {
    prefix ifm;
  }
  
  import huawei-extension {
    prefix ext;
  }

  organization
    "Huawei Technologies Co., Ltd.";
  contact
    "Huawei Industrial Base
     Bantian, Longgang
     Shenzhen 518129
     People's Republic of China
     Website: http://www.huawei.com
     Email: support@huawei.com";
  description
    "ARP FWD configurations and status.";

  revision 2020-06-19 {
    description
      "Initial revision.";
    reference
      "Huawei private.";
  }

  ext:task-name "arp-fwd";

  
  
  augment "/ifm:ifm/ifm:interfaces/ifm:interface" {
    description
      "ARP FWD configurations under ifm interface.";
      container arp-miss-enable
      {
        when "../ifm:type='Vbdif'";
        description
          "Configure ARP miss function in VBDIF.";	  
        leaf enable {
          type boolean;
          default "true";
          description
            "Enable/disable ARP miss function in VBDIF.";
        }
      }
  }
}

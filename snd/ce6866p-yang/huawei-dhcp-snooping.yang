/*
Copyright (C) 2020 Huawei Technologies Co., Ltd. All rights reserved.
*/
submodule huawei-dhcp-snooping {
  belongs-to huawei-dhcp {
    prefix dhcp;
  }
  import huawei-pub-type {
    prefix pub-type;
  }
  import ietf-yang-types {
    prefix yang;
  }
  import huawei-vlan {
    prefix vlan;
  }
  import huawei-network-instance {
    prefix ni;
  }
  import huawei-ifm {
    prefix ifm;
  }
  import huawei-bd {
    prefix bd;
  }
  import ietf-inet-types {
    prefix inet;
  }
  import huawei-extension {
    prefix ext;
  }
  
  organization
    "Huawei Technologies Co., Ltd.";
  contact
    "Huawei Industrial Base
     Bantian, Longgang
     Shenzhen 518129
     People's Republic of China
     Website: http://www.huawei.com
     Email: support@huawei.com";
  description
    "This module contains a collection of YANG definitions for managing DHCP snooping.";
  revision 2020-02-25 {
    description
      "Initial revision.";
    reference
      "Huawei private.";
  }
  typedef dhcp-snooping-port {
    type enumeration {
      enum "bootps" {
        value 0;
        description
          "Bootps(67).";
      }
      enum "bootpc" {
        value 1;
        description
          "Bootpc(68).";
      }
      enum "invalidvalue" {
        value 2;
        description
          "-";
      }
    }
    description
      "The type of DHCP snooping port.";
  }
  grouping dhcp-snooping-type {
    description
      "Configure DHCP snooping attributes.";
    container global {
      description
        "Configure global attributes of DHCP snooping.";
      leaf enable {
        type boolean;
        default "false";
        description
          "Enable/disable DHCP snooping globally.";
      }
      leaf server-detect-enable {
        when "../enable='true'";
        type boolean;
        default "false";
        description
          "Enable/disable the check on bogus DHCP servers.";
      }
      leaf user-bind-auto-save-enable {
        when "../enable='true'";
        type boolean;
        must "(not(../user-bind-auto-save-enable='true') and not(../user-bind-file-name)) or (../user-bind-auto-save-enable='true' and ../user-bind-file-name)";
        default "false";
        description
          "Enable/disable automatic saving of DHCP snooping binding entries.";
      }
      leaf user-bind-file-name {
        when "../enable='true' and ../user-bind-auto-save-enable='true'"; 
        type string {
          length "1..56";
          pattern '(cfcard:/dhcp/\S+\.tbl)';
        }
        description
          "File name of saving the snooping binding table.";
      }
      leaf check-rate-enable {
        when "../enable='true'";
        type boolean;
        default "false";
        description
          "Enable/disable the check on the DHCP packet rate globally.";
      }
      leaf rate-limit {
        when "../enable='true'";
        type uint16 {
          range "1..1000";
        }
        default "100";
        description
          "Global rate of DHCP packets.";
      }
      leaf check-rate-alarm-enable {
        when "../enable='true'";
        type boolean;
        default "false";
        description
          "Enable/disable the rate limit alarm function for DHCP packets globally.";
      }
      leaf rate-threshold {
        when "../enable='true'";
        type uint16 {
          range "1..1000";
        }
        default "100";
        description
          "Global alarm threshold for the DHCP packet rate.";
      }
      leaf alarm-threshold {
        when "../enable='true'";
        type uint16 {
          range "1..1000";
        }
        default "100";
        description
          "Global alarm threshold for DHCP packets.";
      }
      leaf rate-limit-packet-count {
        type uint32;
        default "0";
        config false;
        description
          "Number of discarded packets after the global packet rate limit is reached.";
      }
      leaf user-offline-remove-mac {
        when "../enable='true'";
        type boolean;
        description
          "Enable/disable to delete the MAC address of a DHCP user after the user goes offline.";
      }
      leaf arp-detect-enable {
        type boolean;
        default "false";
        description
          "Enable/disable ARP detection for DHCP users based on DHCP snooping binding entries.";
      }
      leaf global-max-user {
        when "../enable='true'";
        type uint16 {
          range "1..32768";
        }
        default "32768";
        description
          "Maximum number of users globally.";
      }
      leaf snoop-user-transfer-enable {
        when "../enable='true'";
        type boolean;
        description
          "Enable/disable user transfer.";
      }
      leaf mac-strict-check-enable {
        when "../enable='true'";
        type boolean;
        default "false";
        description
          "Enable/disable MAC strict check.";
      }
      leaf unicast-cpu-forward-disable {
        when "../enable='true'";
        type boolean;
        default "false";
        description
          "Enable/disable CPU forwarding for DHCP snooping unicast packets.";
      }
    }
    container committed-access-rate {
      description
        "Configure global attributes of DHCP snooping CAR.";
      leaf car-cir {
        type uint32 {
          range "1..100000000";
        }
        
        description
          "CAR CIR Value.";
      }
      leaf car-cbs {
        type uint32 {
          range "1..536870912";
        }
        description
          "CAR CBS Value.";
      }
    }
    container white-lists {
      description
        "List of whitelists.";
      list white-list {
        key "white-list-name";
        max-elements  "8";
        description
          "Configure a whitelist.";
        leaf white-list-name {
          type string {
            length "1..31";
          }
          description
            "Whitelist name.";
        }
        leaf apply-flag {
          type boolean;
          default "false";
          description
            "Enable/disable to determine whether to use whitelists.";
        }
        container white-rules {
          description
            "List of whitelist rules.";
          list white-rule {
            key "rule-id";
            max-elements  "1023";
            description
              "Configure a whitelist rule.";
            leaf rule-id {
              type uint16 {
                range "1..1023";
              }
              description
                "Whitelist rule ID.";
            }
            leaf source-ip {
              type inet:ipv4-address-no-zone;
              description
                "Source address.";
            }
            leaf source-mask {
              type inet:ipv4-address-no-zone;
              description
                "Source address mask.";
            }
            leaf destination-address {
              type inet:ipv4-address-no-zone;
              description
                "Destination address.";
            }
            leaf destination-mask {
              type inet:ipv4-address-no-zone;
              description
                "Destination address mask.";
            }
            leaf source-port {
              type dhcp-snooping-port;
              description
                "Source port.";
            }
            leaf destination-port {
              type dhcp-snooping-port;
              description
                "Destination port.";
            }
          }
        }
      }
    }
    container dynamic-binds {
      config false;
      description
        "List of statistics of dynamic DHCP snooping binding tables.";
      list dynamic-bind {
        key "ip-address outer-vlan inner-vlan vsi-name vpn-name bridge-domain";
        config false;
        description
          "Statistics of dynamic DHCP snooping binding entries.";
        leaf ip-address {
          type inet:ipv4-address-no-zone;
          config false;
          description
            "User IP address.";
        }
        leaf outer-vlan {
        type leafref {
          path "/vlan:vlan/vlan:vlans/vlan:vlan/vlan:id";
          }
          config false;
          description
            "Outer VLAN ID.";
        }
        leaf inner-vlan {
        type leafref {
          path "/vlan:vlan/vlan:vlans/vlan:vlan/vlan:id";
          }
          config false;
          description
            "Inner VLAN ID.";
        }
        leaf vsi-name {
          type string {
            length "1..31";
          }
          config false;
          description
            "VSI name.";
        }
        leaf vpn-name {
          type leafref {
            path "/ni:network-instance/ni:instances/ni:instance/ni:name";
          }
          config false;
          description
            "VPN name.";
        }
        leaf bridge-domain {
          type leafref {
            path "/bd:bd/bd:instances/bd:instance/bd:id";
          }
          config false;
          description
            "Bridge domain ID.";
        }
        leaf mac-address {
          type pub-type:mac-address {
            length "0..255";
          }
          config false;
          description
            "User MAC address.";
        }
        leaf interface-name {
          type leafref {
            path "/ifm:ifm/ifm:interfaces/ifm:interface/ifm:name";
          }
          config false;
          description
            "Interface name.";
          ext:support-filter "true";
        }
        leaf lease {
          type yang:date-and-time;
          config false;
          description
            "Lease time.";
        }
      }
    }
  }
}
